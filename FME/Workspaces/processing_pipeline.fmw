FME workspace processing_pipeline.fmw

Parameters:
- DestDataset_POSTGRES = SupabaseConnection   # Connection
- message =
- channel_name = test   # Enter Channel Name
- Channel_Polygon = test   # GEOM_TYPE:POLYGON Select Channel Polygon
- is_in_groynvak = YES   # Select Yes/No for is_in_groynvak
- is_bank = YES   # Select Yes/No for is_bank
- is_tidal = YES   # Select Yes/No for is_tidal
- inner_outer_straight = inner   # Select whether channel is on inner bend, outer bend, or straight segment
- channel_connections = 0
- SourceDataset_POSTGIS_5 = SupabaseConnection   # Connection
- SourceDataset_POSTGRES = SupabaseConnection   # Connection
- SourceDataset_GEOPACKAGE_RASTER_3 = /home/ljonker/Documents/geomatics/Synthesis_Project/Data/Bathymetry-Florence.gpkg   # GeoPackage File
- SourceDataset_SHAPEFILE = /home/ljonker/Documents/geomatics/Synthesis_Project/Data/shogun-download/debiet/debietkaart/debietkaart.shp   # Source Esri Shapefile(s)
- SourceDataset_GEOTIFF_3 = /home/ljonker/Documents/geomatics/Synthesis_Project/Data/yearly-classified-geotiffs_classified-image-2024.tif   # Source GeoTIFF File(s) or URL(s)
- SourceDataset_SHAPEFILE_8 = /home/ljonker/Documents/geomatics/Synthesis_Project/Data/All_Inlet_outlet_points/All_inlet_and_outlet.shp   # Source Esri Shapefile(s)
- year = 2026   # What year do you wan't observations for
- SourceDataset_SHAPEFILE_7 = /home/ljonker/Documents/geomatics/Synthesis_Project/Data/Only_Inlet_outlet_points/Only_inlet_and_outlet.shp   # Source Esri Shapefile(s)

Readers:
- POSTGIS_1: POSTGIS from $(SourceDataset_POSTGIS_5)
- POSTGRES_2: POSTGRES from $(SourceDataset_POSTGRES) in Netherlands-RDNew-2008
- GEOPACKAGE_RASTER_2: GEOPACKAGE_RASTER from $(SourceDataset_GEOPACKAGE_RASTER_3)
- SHAPEFILE_1: SHAPEFILE from $(SourceDataset_SHAPEFILE)
- GEOTIFF_1: GEOTIFF from $(SourceDataset_GEOTIFF_3)
- SHAPEFILE_2: SHAPEFILE from $(SourceDataset_SHAPEFILE_8)
- SHAPEFILE_5: SHAPEFILE from $(SourceDataset_SHAPEFILE_7)

Writers:
- POSTGRES_1: POSTGRES to $(DestDataset_POSTGRES)

Note: Shapefile containing the known inlet and outlet points (from VoxView)
Note: Database connection containing tiles, side channels, observations, etc.
Note: Bathymetric data 2024 and 2025, for the usable side channels (side channels with data for both years)
Only_inlet_and_outlet (reader SHAPEFILE_5)
    attributes: objectid varchar(254), objectname varchar(254), linkedcomp varchar(254), yearof_con varchar(254), riskscore varchar(254), risklevel varchar(254), objectcond varchar(254), typeid varchar(254), typename varchar(254), faultcount number(19,0), ultimourl varchar(254), timestamp varchar(254), objectlati varchar(254), objectlong varchar(254), objectowne varchar(254), objectmana varchar(254)
    -> Flow_Direction [inlet_outlet_points]
    -> Distance_from_Inlet [inlet_outlet_points]
Note: Shapefile containing the known inlet and outlet points (from VoxView), in addition to manually added inlet and outlet points if data was missing (for the purpose of length calculation)
All_inlet_and_outlet (reader SHAPEFILE_2)
    attributes: scid varchar(80), objectname varchar(80)
    -> Channel_Length__And_Relative_Length [inlet_outlet_input]
Note: Combined version of debietkaart layers found on VoxView, in the Algemeen 2025 project. They were merged into one shapefile for convenience, with an attribute added for min and max debiet
debietkaart (reader SHAPEFILE_1)
    attributes: fid long, OBJECTID number(19,0), Id number(19,0), gridcode number(19,0), Resultaat varchar(254), ORIG_FID number(19,0), Shape_Leng number(33,15), Shape_Area number(33,15), Q__clipped varchar(254), layer varchar(254), path varchar(254), min_debiet long, max_debiet long
    -> Debiet [debietkaart_input]
Note: Observations : Passed
Note: This node collects the values that are written to the 'observations' table in the database.
Note: Take care that for a given year, an observation is made for a channel before trying to write tile observations
Junction_5
    -> Join_to_observation [RIGHT]
    -> Join_to_observation_3 [RIGHT]
Note: Some features are written directly to the DB and aren't included in this script / - Channel connections / - Groinvak / - Tidal / - Bank / -Inner/Outer / - Name
Note: ObservationIds : Output
Note: This node collects the values that are written to the 'side_channels' table in the database. These are 'static' features that should only need to be run once (or perhaps overwritten periodically if you get updated information)
Note: This node collects the values that are written to the 'tiles' table in the database. These are 'static' features that should only need to be run once (or perhaps overwritten periodically if you get updated information)
Note: This node collects the values that are written to the 'tile_observations' table in the database. Given the volume of data in the incoming features, it is possible you will run out of memory if you run all at once. Running one by one and caching each feature result can mitigate this / Note also how you use the database writer, make sure to set it to "update" mode for the updating features, and insert mode if inserting new features
Junction_7
    -> Join_to_observation_2 [RIGHT]
Note: 2024 data, if using, ensure that this node is attached to correct inputs AND 2024 observations are attached to DB writer
Junction
Note: Vegetation data based on raster provided by RWS 'Vegitatie Monitor'. / https://vegetatiemonitor.rijkswaterstaat.nl/#/voorspel
Note: 2025 data, if using, ensure that this node is attached to correct inputs AND 2025 observations are attached to DB writer
Junction_2
    -> Junction_3
Junction_3
    -> Roughness [bathymetry_input]
    -> Bed_Level [bathymetry_input]
    -> Slope [bathymetry_input]
    -> Aspect [bathymetry_input]

Bookmark: Bathymetric Data (averages)
26 Langsdam Ophemert Bathy 24-04-10 (reader GEOPACKAGE_RASTER_2)
    -> Junction
26 Langsdam Ophemert Bathy 25-02-17 (reader GEOPACKAGE_RASTER_2)
    -> Junction_2
01 Afferden en Deest Bathy 24-04-10 (reader GEOPACKAGE_RASTER_2)
    -> Junction
01 Afferden en Deest Bathy 25-xx-xx (reader GEOPACKAGE_RASTER_2)
    -> Junction_2
03 Avelingerdiep Bathy 24-02-02 (reader GEOPACKAGE_RASTER_2)
    -> Junction
03 Avelingerdiep Bathy 25-03-20 (reader GEOPACKAGE_RASTER_2)
    -> Junction_2
06 Beneden Leeuwen Bathy 24-03-15 (reader GEOPACKAGE_RASTER_2)
    -> Junction
06 Beneden Leeuwen Bathy 25-02-27 (reader GEOPACKAGE_RASTER_2)
    -> Junction_2
07 Blauwe Kamer Bathy 24-04-17 (reader GEOPACKAGE_RASTER_2)
    -> Junction
07 Blauwe Kamer Bathy 25-04-09 (reader GEOPACKAGE_RASTER_2)
    -> Junction_2
08 Bossenwaard Bathy 24-04-16 (reader GEOPACKAGE_RASTER_2)
    -> Junction
08 Bossenwaard Bathy 25-04-11 (reader GEOPACKAGE_RASTER_2)
    -> Junction_2
09 Brakel Oost Bathy 24-04-25 (reader GEOPACKAGE_RASTER_2)
    -> Junction
09 Brakel Oost Bathy 25-02-27 (reader GEOPACKAGE_RASTER_2)
    -> Junction_2
10 Brakel West Bathy 24-04-11 (reader GEOPACKAGE_RASTER_2)
    -> Junction
10 Brakel West Bathy 25-09-30 (reader GEOPACKAGE_RASTER_2)
    -> Junction_2
11 Dordtsche Avelingen Bathy 24-02-02 (reader GEOPACKAGE_RASTER_2)
    -> Junction
11 Dordtsche Avelingen Bathy 25-02-19 (reader GEOPACKAGE_RASTER_2)
    -> Junction_2
12 Elster Buitenwaarden AHN 25-04-18 (reader GEOPACKAGE_RASTER_2)
    -> Junction_2
12 Elster Buitenwaarden K10 23-10-02 (reader GEOPACKAGE_RASTER_2)
    -> Junction
13 Everdingerwaard Bathy 24-04-25 (reader GEOPACKAGE_RASTER_2)
    -> Junction
13 Everdingerwaard Bathy 25-04-28 (reader GEOPACKAGE_RASTER_2)
    -> Junction_2
17 Graafsche Waard Bathy 24-04-16 (reader GEOPACKAGE_RASTER_2)
    -> Junction
17 Graafsche Waard Bathy 25-04-08 (reader GEOPACKAGE_RASTER_2)
    -> Junction_2
19 Heeselt Oost Bathy 24-03-14 (reader GEOPACKAGE_RASTER_2)
    -> Junction
19 Heeselt Oost Bathy 25-03-23 (reader GEOPACKAGE_RASTER_2)
    -> Junction_2
24 Klompenwaard Bathy 24-xx-xx (reader GEOPACKAGE_RASTER_2)
    -> Junction
24 Klompenwaard Bathy 25-xx-xx (reader GEOPACKAGE_RASTER_2)
    -> Junction_2
36 Palmerswaard Bathy 24-04-18 (reader GEOPACKAGE_RASTER_2)
    -> Junction
36 Palmerswaard Bathy 25-04-18 (reader GEOPACKAGE_RASTER_2)
    -> Junction_2
41 Schoutenwaard Bathy 24-xx-xx (reader GEOPACKAGE_RASTER_2)
    -> Junction
41 Schoutenwaard Bathy 25-01-30 (reader GEOPACKAGE_RASTER_2)
    -> Junction_2
42 Spiegelwaal Bathy 24-xx-xx (reader GEOPACKAGE_RASTER_2)
    -> Junction
42 Spiegelwaal Bathy 25-xx-xx (reader GEOPACKAGE_RASTER_2)
    -> Junction_2
43 Stadswaard Bathy 24-xx-xx (reader GEOPACKAGE_RASTER_2)
    -> Junction
43 Stadswaard Bathy 25-01-30 (reader GEOPACKAGE_RASTER_2)
    -> Junction_2
48 Waalse Waard Bathy 24-04-16 (reader GEOPACKAGE_RASTER_2)
    -> Junction
48 Waalse Waard Bathy 25-04-11 (reader GEOPACKAGE_RASTER_2)
    -> Junction_2
49 Willige Langerak Bathy 24-11-11 (reader GEOPACKAGE_RASTER_2)
    -> Junction
49 Willige Langerak Bathy 25-04-08 (reader GEOPACKAGE_RASTER_2)
    -> Junction_2
02 Avelingen Bathy 24-xx-xx (reader GEOPACKAGE_RASTER_2)
    -> Junction
02 Avelingen Bathy 25-03-19 (reader GEOPACKAGE_RASTER_2)
    -> Junction_2
05 Bakenhof Bathy 24-02-16 (reader GEOPACKAGE_RASTER_2)
    -> Junction
05 Bakenhof Bathy 25-01-27 (reader GEOPACKAGE_RASTER_2)
    -> Junction_2
28 Lexmond Bathy 24-04-16 (reader GEOPACKAGE_RASTER_2)
    -> Junction
28 Lexmond Bathy 25-04-08 (reader GEOPACKAGE_RASTER_2)
    -> Junction_2
37 Pannerden Bathy 24-03-20 (reader GEOPACKAGE_RASTER_2)
    -> Junction
37 Pannerden Bathy 25-01-24 (reader GEOPACKAGE_RASTER_2)
    -> Junction_2
39 Pontwaard Bathy 24-04-16 (reader GEOPACKAGE_RASTER_2)
    -> Junction
39 Pontwaard Bathy 25-04-08 (reader GEOPACKAGE_RASTER_2)
    -> Junction_2
40 Salmsteke Bathy 24-11-11 (reader GEOPACKAGE_RASTER_2)
    -> Junction
40 Salmsteke Bathy 25-02-13 (reader GEOPACKAGE_RASTER_2)
    -> Junction_2

Bookmark: Database
side_channels (reader POSTGIS_1)
    attributes: scid int4,PrimaryKey, name varchar(254), area float4, perimeter float4, groynevak bool, channel_connections int2, tidal bool, Bank bool, channel_length float4, inner_outer text
    -> Debiet [channel_polygon_input]
    -> Roughness [channel_polygon_input]
    -> Bed_Level [channel_polygon_input]
    -> Slope [channel_polygon_input]
    -> Aspect [channel_polygon_input]
    -> Vegetation [channel_polygon_input]
    -> Channel_Length__And_Relative_Length [channel_polygon_input]
    -> Width [channel_polygon_input]
    -> Area_and_Perimeter [channel_polygon_input]
    -> Flow_Direction [channel_polygon_input]
    -> Distance_from_Inlet [channel_polygon_input]
    -> Distance_to_Bank [channel_polygon_input]
tiles (reader POSTGIS_1)
    attributes: tid int4,PrimaryKey, left int8, top int8, right int8, bottom int8, scid int4, min_flow_threshold int8, width float4
    -> Debiet [tile_input]
    -> Roughness [tile_input]
    -> Bed_Level [tile_input]
    -> Slope [tile_input]
    -> Aspect [tile_input]
    -> Width [tile_input]
    -> Flow_Direction [tile_input]
    -> Distance_from_Inlet [tile_input]
    -> Distance_to_Bank [tile_input]
observations (reader POSTGRES_2)
    attributes: oid serial,PrimaryKey, scid int4, date date, year int4
    -> Observations_For_year
Note: Ensure that you set the year correctly when writing observations to the database (assuming you are updating) / If you are inserting than it should generate the IDs for you
Observations_For_year: Tester
    BOOL_OP = OR
    TEST_CLAUSE = TEST @Value(year) = $(year)
    TEST_MODE = TEST
    PASSED -> Junction_4
Note: Join_to_observation : Right
Junction_4
    -> Junction_5
tile_observations (reader POSTGRES_2)
    attributes: toid int4,PrimaryKey, tid int4, slope float8, roughness float4, bed_level float4, oid int4, aspect float4
    -> ObservationIds
ObservationIds: AttributeManager
    ATTR_TABLE:
      REMOVE slope (real64)
      REMOVE roughness (real32)
      REMOVE bed_level (real32)
      REMOVE aspect (real32)
    -> Junction_6
Note: Join_to_observation_2 : Right
Junction_6
    -> Junction_7

Bookmark: Channel Level
Channel_Length__And_Relative_Length: Channel Length and Relative Length
    OBJECTNAME = @Value(objectname)
    SCID = @Value(scid)
    relative_channel_length -> side_channels (writer POSTGRES_1)
Area_and_Perimeter: Area and Perimeter
    NAME = @Value(name)
    SCID = @Value(scid)
    perimeter_and_area -> side_channels (writer POSTGRES_1)

Bookmark: Write To Side Channels
side_channels (writer POSTGRES_1)
    attributes: area float8, perimeter float8, name varchar(254), scid int4,PrimaryKey, relative_channel_length float8

Bookmark: Tile Level
Width
    BOTTOM = @Value(bottom)
    LEFT = @Value(left)
    NAME = @Value(name)
    RIGHT = @Value(right)
    TID = @Value(tid)
    TOP = @Value(top)
    Width -> tiles (writer POSTGRES_1)
Debiet
    min_flow_threshold -> tiles (writer POSTGRES_1)
Flow_Direction: Flow Direction
    FAULTCOUNT = @Value(faultcount)
    LEFT = @Value(left)
    LINKEDCOMP = @Value(linkedcomp)
    NAME = @Value(name)
    OBJECTCOND = @Value(objectcond)
    OBJECTID = @Value(objectid)
    OBJECTLATI = @Value(objectlati)
    OBJECTLONG = @Value(objectlong)
    OBJECTMANA = @Value(objectmana)
    OBJECTNAME = @Value(objectname)
    OBJECTOWNE = @Value(objectowne)
    RIGHT = @Value(right)
    RISKLEVEL = @Value(risklevel)
    RISKSCORE = @Value(riskscore)
    SCID = @Value(scid)
    TIMESTAMP = @Value(timestamp)
    TYPEID = @Value(typeid)
    TYPENAME = @Value(typename)
    ULTIMOURL = @Value(ultimourl)
    YEAROF_CON = @Value(yearof_con)
    flow_direction -> tiles (writer POSTGRES_1)
Distance_from_Inlet: Distance from Inlet
    BOTTOM = @Value(bottom)
    FAULTCOUNT = @Value(faultcount)
    LEFT = @Value(left)
    LINKEDCOMP = @Value(linkedcomp)
    NAME = @Value(name)
    OBJECTCOND = @Value(objectcond)
    OBJECTID = @Value(objectid)
    OBJECTLATI = @Value(objectlati)
    OBJECTLONG = @Value(objectlong)
    OBJECTMANA = @Value(objectmana)
    OBJECTNAME = @Value(objectname)
    OBJECTOWNE = @Value(objectowne)
    RIGHT = @Value(right)
    RISKLEVEL = @Value(risklevel)
    RISKSCORE = @Value(riskscore)
    SCID = @Value(scid)
    TIMESTAMP = @Value(timestamp)
    TOP = @Value(top)
    TYPEID = @Value(typeid)
    TYPENAME = @Value(typename)
    ULTIMOURL = @Value(ultimourl)
    YEAROF_CON = @Value(yearof_con)
    distance_from_inlet -> tiles (writer POSTGRES_1)
Distance_to_Bank: Distance to Bank
    BOTTOM = @Value(bottom)
    LEFT = @Value(left)
    NAME = @Value(name)
    RIGHT = @Value(right)
    SCID = @Value(scid)
    TOP = @Value(top)
    distance_to_bank -> tiles (writer POSTGRES_1)

Bookmark: Write To Tiles
tiles (writer POSTGRES_1)
    attributes: flow_direction float8, tid int4,PrimaryKey, scid int4,PrimaryKey, distance_to_bank float8, width float8, min_flow_threshold int4, distance_from_inlet float8

Bookmark: 2024
GEOTIFF (reader GEOTIFF_1)
    -> Vegetation [vegetation_raster_input]

Bookmark: Channel Level
Vegetation
    SCID = @Value(scid)
    vegetation_percentage -> Join_to_observation_3 [LEFT]

Bookmark: Write To Observations
Join_to_observation_3: FeatureJoiner
    ATTR_CONFLICT_RES_LOOKUP = USE_LEFT
    GEOMETRY_HANDLING_LOOKUP = USE_LEFT
    JOIN_KEYS = scid scid AUTO
    JOIN_MODE = Inner
    ATTR_CONFLICT_RES = Prefer Left
    GEOMETRY_HANDLING = Prefer Left
    JOINED -> Updating_Features_2
Updating_Features_2: AttributeManager
    ATTR_TABLE:
      REMOVE date (date)
      REMOVE year (int8)
    -> observations (writer POSTGRES_1)
observations (writer POSTGRES_1)
    attributes: scid varchar(200), oid serial,PrimaryKey, vegetation_percentage float8

Bookmark: Tile Level
Roughness
    BOTTOM = @Value(bottom)
    FME_BASENAME = @Value(fme_basename)
    LEFT = @Value(left)
    RIGHT = @Value(right)
    TID = @Value(tid)
    TOP = @Value(top)
    roughness -> Combine_tile_observations
Bed_Level: Bed Level
    BOTTOM = @Value(bottom)
    FME_BASENAME = @Value(fme_basename)
    LEFT = @Value(left)
    RIGHT = @Value(right)
    TID = @Value(tid)
    TOP = @Value(top)
    bed_level -> Combine_tile_observations
Slope
    BOTTOM = @Value(bottom)
    FME_BASENAME = @Value(fme_basename)
    LEFT = @Value(left)
    RIGHT = @Value(right)
    TID = @Value(tid)
    TOP = @Value(top)
    slope -> Combine_tile_observations
Aspect
    BOTTOM = @Value(bottom)
    FME_BASENAME = @Value(fme_basename)
    LEFT = @Value(left)
    RIGHT = @Value(right)
    TID = @Value(tid)
    TOP = @Value(top)
    aspect -> Combine_tile_observations

Bookmark: Write To Tile Observations
Combine_tile_observations: Aggregator
    ACCUM_ATTRS = All
    GROUP_BY = tid
    MODE = Attributes Only
    SEP = ,
    AGGREGATE -> Join_to_observation [LEFT]
Join_to_observation: FeatureJoiner
    ATTR_CONFLICT_RES_LOOKUP = USE_LEFT
    GEOMETRY_HANDLING_LOOKUP = USE_LEFT
    JOIN_KEYS = scid scid AUTO
    JOIN_MODE = Inner
    ATTR_CONFLICT_RES = Prefer Left
    GEOMETRY_HANDLING = Prefer Left
    JOINED -> Join_to_observation_2 [LEFT]
Join_to_observation_2: FeatureJoiner
    ATTR_CONFLICT_RES_LOOKUP = USE_LEFT
    GEOMETRY_HANDLING_LOOKUP = USE_LEFT
    JOIN_KEYS = oid oid AUTO tid tid AUTO
    JOIN_MODE = Inner
    ATTR_CONFLICT_RES = Prefer Left
    GEOMETRY_HANDLING = Prefer Left
    JOINED -> Updating_Features
    UNJOINED_LEFT -> Inserting_Features
Updating_Features: AttributeManager
    ATTR_TABLE:
      REMOVE date (date)
      REMOVE year (int32)
      REMOVE tid (int32)
      REMOVE oid (int32)
Inserting_Features: AttributeManager
    ATTR_TABLE:
      REMOVE date (date)
      REMOVE year (int32)
    -> tile_observations (writer POSTGRES_1)
tile_observations (writer POSTGRES_1)
    attributes: tid varchar(200), bed_level float8, scid int4, roughness float8, slope float8, aspect float8, oid serial,PrimaryKey

FME custom transformer Bed Level
This feature directly writes the average bed level per tile, aggregated over the 5x5m area
This is a dynamic feature, and should be updated yearly

Parameters:
- RIGHT = @Value(right)   # right
- TID = @Value(tid)   # tid
- LEFT = @Value(left)   # left
- BOTTOM = @Value(bottom)   # bottom
- TOP = @Value(top)   # top
- FME_BASENAME = @Value(fme_basename)   # Fme Basename

channel_polygon_input (input)
    -> clipped_to_polygon_2 [CLIPPER]
bathymetry_input (input)
    -> clipped_to_polygon_2 [CANDIDATE]
Note: Already written to DB: / 2024 / 2025
bed_level (output)

Bookmark: Clipped bed level
clipped_to_polygon_2: Clipper
    ADD_NODATA = NO
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterBandMinMaxExtractor
RasterBandMinMaxExtractor
    -> filter_nodata_2
filter_nodata_2: Tester
    BOOL_OP = COMPOSITE
    COMPOSITE_TEST = 1 AND 2
    TEST_CLAUSE:
      TEST @Value(_band{0}.max) NOT_= 9999
      TEST @Value(_band{0}.min) NOT_= 9999
    TEST_MODE = TEST
    PASSED -> Raster_Cell_to_Point

Bookmark: Bed Level
Raster_Cell_to_Point: RasterCellCoercer
    CELL_GEOMETRY = Points
    EXTRACT_NODATA = No
    EXTRACT_VALUES_AS_ATTRIBUTES = Yes
    PRESERVE_ATT = YES
    CELL_GEOMETRY_LOOKUP = Points
    EXTRACT_BAND_VALUES_AS = Attributes
    EXTRACT_NODATA_LOOKUP = No
    PRESERVE_ATTRIBUTES = Yes
    -> PointOnAreaOverlayer_2 [POINT]
tile_input (input)
    -> PointOnAreaOverlayer_2 [AREA]
PointOnAreaOverlayer_2
    ATTR_ACCUM_MODE = HANDLE_CONFLICT
    ATTR_CONFLICT_RES = ORIGINAL_IF_CONFLICT
    DEAGGREGATE_INPUT = Yes
    OV_ATTR = _overlaps
    POLYS_FIRST = NO
    POINT -> StatisticsCalculator_2
StatisticsCalculator_2
    ATTR_ACCUM_MODE = All
    CALCULATION_MODE = NUMERIC
    FEAT_STATS = _band{0}.value,NUMERIC_MODE,,,,,MEAN,,,,,,,,
    GROUP_BY = tid
    SUMMARY -> RemoveData_outside_of_tiles_2
RemoveData_outside_of_tiles_2: Tester
    BOOL_OP = OR
    TEST_CLAUSE = TEST tid NOT_ATTRIBUTE_IS_MISSING ""
    TEST_MODE = TEST
    PASSED -> Rename_Attrubute
Rename_Attrubute: AttributeManager
    ATTR_TABLE:
      RENAME_SET_VALUE _band{0}.value.mean > bed_level (real64)
      REMOVE _band{}.value.mean (varchar(200))
      REMOVE fme_basename (buffer)
      REMOVE _clipped (char(3))
      REMOVE _band{}.min (buffer)
      REMOVE _band{}.max (real64)
      REMOVE _band{}.palette{}.keyMin (buffer)
      REMOVE _band{}.palette{}.keyMax (buffer)
      REMOVE _band{}.palette{}.valueMin (real64)
      REMOVE _band{}.palette{}.valueMax (real64)
      REMOVE _band{}.value (real64)
      REMOVE _band{}.palette{}.value (real64)
      REMOVE left (int64)
      REMOVE top (int64)
      REMOVE right (int64)
      REMOVE bottom (int64)
      REMOVE _overlaps (uint32)
    USER_EXPOSED_ATTRIBUTES = gid
    -> Round_Attribute_2
Round_Attribute_2: AttributeRounder
    PLACES = 4
    ROUND_TYPE_TCL = round
    SRC_ATTRS = bed_level
    ROUND_TYPE = Nearest
    -> bed_level (output)

Bookmark: Notes on feature
Note: This feature directly writes the average bed level per tile, aggregated over the 5x5m area / This is a dynamic feature, and should be updated yearly

FME custom transformer Distance from Inlet

Parameters:
- RIGHT = @Value(right)   # right
- RISKLEVEL = @Value(risklevel)   # risklevel
- OBJECTID = @Value(objectid)   # objectid
- TYPEID = @Value(typeid)   # typeid
- OBJECTMANA = @Value(objectmana)   # objectmana
- FAULTCOUNT = @Value(faultcount)   # faultcount
- SCID = @Value(scid)   # scid
- LINKEDCOMP = @Value(linkedcomp)   # linkedcomp
- LEFT = @Value(left)   # left
- TYPENAME = @Value(typename)   # typename
- NAME = @Value(name)   # name
- ULTIMOURL = @Value(ultimourl)   # ultimourl
- RISKSCORE = @Value(riskscore)   # riskscore
- YEAROF_CON = @Value(yearof_con)   # Yearof Con
- TOP = @Value(top)   # top
- BOTTOM = @Value(bottom)   # bottom
- OBJECTLATI = @Value(objectlati)   # objectlati
- OBJECTLONG = @Value(objectlong)   # objectlong
- TIMESTAMP = @Value(timestamp)   # timestamp
- OBJECTNAME = @Value(objectname)   # objectname
- OBJECTOWNE = @Value(objectowne)   # objectowne
- OBJECTCOND = @Value(objectcond)   # objectcond

channel_polygon_input (input)
    -> Reprojector_3
    -> NeighborFinder_3 [CANDIDATE]
inlet_outlet_points (input)
    -> Inlet_2
Note: Already written to DB
distance_from_inlet (output)

Bookmark: Make centreline
Reprojector_3
    DEST = Amersfoort-RDNew
    INTERPOLATION_TYPE = NearestNeighbor
    RASTER_CELL_SIZE = PreserveCells
    RASTER_TOLERANCE = 0.0
    REPROJECTED -> CenterlineReplacer
CenterlineReplacer
    MODE = APPROX_CENTER_LINE
    CENTERLINE -> Deaggregator_3
    CENTERLINE -> Generalizer
Generalizer
    ALG = Douglas
    PRESERVE = No
    PRESERVE_PATHS_LOOKUP = NO
    TOLERANCE = 3
    ALG_TEXT = Douglas (Generalize)
    PRESERVE_PATHS = No
    -> Clipper_2 [CANDIDATE]

Bookmark: chop centreline into line pieces
Deaggregator_3
    ATTR_ACCUM_MODE = HANDLE_CONFLICT
    ATTR_CONFLICT_RES = INCOMING_IF_CONFLICT
    EXPLODE_INSTANCES = Yes
    GEOM_LABEL_FIELD = _geometry_label
    LIST_ATTR_MODE_LOOKUP = LEAN
    PART_NUMBER_FIELD = _part_number
    RECURSIVE = No
    SPLIT_COMPOSITES = Yes
    DEAGGREGATED -> Chopper
Chopper
    DEAGGREGATE_INPUT = Deaggregate
    MAX_VERTICES = 2
    MODE_LOOKUP = VERTEX
    REMNANT_ATTR = _remnant
    MODE = By Vertex
    CHOPPED -> ShortestPathFinder_2 [NETWORK]

Bookmark: Inlet
Inlet_2: Tester
    BOOL_OP = OR
    TEST_CLAUSE = CASE_INSENSITIVE_TEST @Value(objectname) BEGINS_WITH Inlaat
    TEST_MODE = CASE_INSENSITIVE_TEST
    PASSED -> Reprojector
Reprojector
    DEST = Amersfoort-RDNew
    INTERPOLATION_TYPE = NearestNeighbor
    RASTER_CELL_SIZE = PreserveCells
    RASTER_TOLERANCE = 0.0
    REPROJECTED -> NeighborFinder_3 [BASE]
NeighborFinder_3
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> VertexCreator_7
VertexCreator_7
    MEASURE_TYPE_LOOKUP = CONTINUOUS
    MODE = REPLACE
    REMOVE_ATTRIBUTES = No
    XVAL = @Value(_closest_base_x)
    YVAL = @Value(_closest_base_y)
    MEASURE_TYPE = Continuous
    MODE_NAME = Replace with Point
    -> AttributeCreator
AttributeCreator
    ATTR_TABLE = SET_TO _path_role (varchar(4)) = From
    -> FeatureMerger_2 [SUPPLIER]
    -> Junction_3
Note: FeatureJoiner : Right
Junction_3
    -> Junction_4

Bookmark: Find distance from inlet per crossing tile of centreline
Note: AttributeCreator : Output
Junction_4
    -> FeatureJoiner [RIGHT]
Note: tile_input
Junction_2
    -> FeatureJoiner [LEFT]
FeatureJoiner
    ATTR_CONFLICT_RES_LOOKUP = USE_LEFT
    GEOMETRY_HANDLING_LOOKUP = USE_LEFT
    JOIN_KEYS = scid scid AUTO
    JOIN_MODE = Inner
    ATTR_CONFLICT_RES = Prefer Left
    GEOMETRY_HANDLING = Prefer Left
    JOINED -> PointOnAreaOverlayer [AREA]
ShortestPathFinder_2
    ALLOW_UTURNS = Yes
    LIST_ATTRS_TO_INCLUDE = scid
    REORDER_MODE = NONE
    SEGMENT_LIST_NAME = segment attributes
    SNAP_POINTS = Yes
    SNAP_TOLERANCE = 200
    THREE_D = No
    WEIGHT_ATTR_CHOICE = BY_LENGTH
    PATH -> AttributeManager_4
AttributeManager_4
    ATTR_TABLE:
      REMOVE segment attributes{}.scid (int32)
      REMOVE name (varchar(254))
      REMOVE _clipped (char(3))
      REMOVE _part_number (uint64)
      REMOVE _geometry_label (buffer)
      REMOVE _indices{}.x (real64)
      REMOVE _indices{}.y (real64)
      REMOVE _indices{}.z (real64)
      REMOVE last_element (real64)
      REMOVE _path_role (varchar(2))
      REMOVE objectname (varchar(254))
      REMOVE _distance (real64)
      REMOVE _angle (real64)
      REMOVE _candidate_angle (real64)
      REMOVE _candidate_label_angle (real64)
      REMOVE _closest_candidate_x (real64)
      REMOVE _closest_candidate_y (real64)
      REMOVE segment attributes{}._direction (buffer)
      RENAME_SET_VALUE _total_cost > distance_from_inlet (real64)
    USER_EXPOSED_ATTRIBUTES = area,inner_outer
    -> VertexCreator_6
VertexCreator_6
    MEASURE_TYPE_LOOKUP = CONTINUOUS
    MODE = REPLACE
    REMOVE_ATTRIBUTES = No
    XVAL = @Value(x_mid)
    YVAL = @Value(y_mid)
    MEASURE_TYPE = Continuous
    MODE_NAME = Replace with Point
    -> PointOnAreaOverlayer [POINT]
PointOnAreaOverlayer
    ATTR_ACCUM_MODE = HANDLE_CONFLICT
    ATTR_CONFLICT_RES = ORIGINAL_IF_CONFLICT
    DEAGGREGATE_INPUT = Yes
    OV_ATTR = _overlaps
    POLYS_FIRST = NO
    AREA -> Split_tiles_into_if_it_has_a_distance_value

Bookmark: Distance from inlet
tile_input (input)
    -> Clipper_2 [CLIPPER]
    -> Chopper
    -> Junction
Note: FeatureJoiner : Left
Junction
    -> Junction_2

Bookmark: Chop centreline into tile pieces
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> CoordinateExtractor
CoordinateExtractor
    LIST_NAME = _indices
    RECURSIVE = Yes
    MODE = All Coordinates
    -> AttributeManager_3
AttributeManager_3
    ATTR_TABLE:
      SET_TO last_element (real64) = @Evaluate(@NumCoords()-2)
      SET_TO x_mid (real64) = @Evaluate((@Value(_indices{0}.x)+@Value(_indices{@Value(last_element)}.x))/2)
      SET_TO y_mid (real64) = @Evaluate((@Value(_indices{0}.y)+@Value(_indices{@Value(last_element)}.y))/2)
      SET_TO _path_role (varchar(2)) = To
    -> Counter
Counter
    CNT_ATTR = _count
    DOMAIN = counter
    SCOPE = Global
    START = 0
    -> FeatureMerger_2 [REQUESTOR]

Bookmark: Create from to paths
FeatureMerger_2
    ATTR_ACCUM_MODE = Merge Supplier
    ATTR_CONFLICT_RES_LOOKUP = REQUESTOR_IF_CONFLICT
    IGNORE_NULLS = No
    JOIN_KEYS = @Value(scid) @Value(scid) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> VertexCreator_2
    MERGED -> VertexCreator_5
VertexCreator_2
    MEASURE_TYPE_LOOKUP = CONTINUOUS
    MODE = REPLACE
    REMOVE_ATTRIBUTES = No
    XVAL = @Value(_closest_base_x)
    YVAL = @Value(_closest_base_y)
    MEASURE_TYPE = Continuous
    MODE_NAME = Replace with Point
    -> LineBuilder_3
VertexCreator_5
    COORDSYS = Amersfoort-RDNew
    MEASURE_TYPE_LOOKUP = CONTINUOUS
    MODE = REPLACE
    REMOVE_ATTRIBUTES = No
    XVAL = @Value(x_mid)
    YVAL = @Value(y_mid)
    MEASURE_TYPE = Continuous
    MODE_NAME = Replace with Point
    -> LineBuilder_3
    <REJECTED> -> Junction_8
LineBuilder_3
    ACCUM_INPUT_ATTRS_LOOKUP = One
    GROUP_BY = scid _count
    REMOVE_DUPLICATES_LOOKUP = NO
    ACCUM_INPUT_ATTRS = Use Attributes From One Feature
    REMOVE_DUPLICATES = No
    LINE -> ShortestPathFinder_2 [FROM-TO]
Junction_8

Bookmark: Give value to the other tiles
Split_tiles_into_if_it_has_a_distance_value: Tester
    BOOL_OP = OR
    TEST_CLAUSE = TEST distance_from_inlet ATTRIBUTE_IS_MISSING ""
    TEST_MODE = TEST
    PASSED -> Give_empty_tiles_the_nearest_neighbor_value [BASE]
    FAILED -> Give_empty_tiles_the_nearest_neighbor_value [CANDIDATE]
    FAILED -> Tester_4
Give_empty_tiles_the_nearest_neighbor_value: NeighborFinder
    ATTR_ACCUM_MODE = Merge Candidate
    ATTR_CONFLICT_RES = Use Base
    CANDIDATES_FIRST = No
    GROUP_BY = scid
    INSERT_VERTEX = No
    MEASURES_FROM_CANDIDATE = Yes
    MEASURE_TYPE = Continuous
    MODE = Bases and Candidates
    TREAT_POLYGON_AS = Lines
    MATCHED -> Tester_4
Tester_4
    BOOL_OP = OR
    TEST_CLAUSE = TEST tid NOT_ATTRIBUTE_IS_MISSING ""
    TEST_MODE = TEST
    PASSED -> AttributeManager_5
AttributeManager_5
    ATTR_TABLE:
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE scid (int32)
      REMOVE x_mid (real64)
      REMOVE y_mid (real64)
      REMOVE _count (int64)
      REMOVE left (int64)
      REMOVE top (int64)
      REMOVE right (int64)
      REMOVE bottom (int64)
      REMOVE _overlaps (uint32)
      REMOVE objectid (varchar(254))
      REMOVE linkedcomp (varchar(254))
      REMOVE yearof_con (varchar(254))
      REMOVE riskscore (varchar(254))
      REMOVE risklevel (varchar(254))
      REMOVE objectcond (varchar(254))
      REMOVE typeid (varchar(254))
      REMOVE typename (varchar(254))
      REMOVE faultcount (number(19,0))
      REMOVE ultimourl (varchar(254))
      REMOVE timestamp (varchar(254))
      REMOVE objectlati (varchar(254))
      REMOVE objectlong (varchar(254))
      REMOVE objectowne (varchar(254))
      REMOVE objectmana (varchar(254))
      REMOVE _path_role (varchar(4))
      REMOVE objectname (varchar(254))
      REMOVE name (varchar(254))
    USER_EXPOSED_ATTRIBUTES = gid,width.mean
    -> AttributeRounder
AttributeRounder
    PLACES = 3
    ROUND_TYPE_TCL = round
    SRC_ATTRS = distance_from_inlet
    ROUND_TYPE = Nearest
    -> distance_from_inlet (output)

Bookmark: Notes on feature
Note: This feature calculates the distance of a tile from the inlet of the side channel. This is derived by calculating the side channels centerline, and then generating shortest paths between the channel inlet point and many target points along that centerline. The length of that shortest path is then the distance from the inlet. / For tiles that do not directly have a target point, they take the distance of their nearest neighbor. / Note that for disconnected segments of some channels (such as separate ponds that are a part of the same channel) they will recieve a value associated with the closest part of the channel with a value. / This is a static feature (does not update). If this eventually becomes a feature that is update more frequently (yearly) then it should be moved to the observations table instead.

FME custom transformer Debiet
This feature takes the lower bound of each debiet layer, and associates it with the closest tile. Thus for each tile we know approximately when it begins to co-flow.
This is a static feature (does not update). If this eventually becomes a feature that is update more frequently (yearly) then it should be moved to the tile_observation table instead.

channel_polygon_input (input)
    -> Clipper [CLIPPER]
debietkaart_input (input)
    -> Clipper [CANDIDATE]
Note: Already written to DB
min_flow_threshold (output)

Bookmark: Debiet
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> PointOnAreaOverlayer_3 [AREA]
tile_input (input)
    -> CenterPointReplacer
CenterPointReplacer
    POINTTYPE = CENTER
    POINT -> PointOnAreaOverlayer_3 [POINT]
PointOnAreaOverlayer_3
    ATTR_ACCUM_MODE = HANDLE_CONFLICT
    ATTR_CONFLICT_RES = ORIGINAL_IF_CONFLICT
    DEAGGREGATE_INPUT = Yes
    OV_ATTR = _overlaps
    POLYS_FIRST = NO
    POINT -> RemoveData_outside_of_tiles
RemoveData_outside_of_tiles: Tester
    BOOL_OP = OR
    TEST_CLAUSE = TEST tid NOT_ATTRIBUTE_IS_MISSING ""
    TEST_MODE = TEST
    PASSED -> AttributeManager
AttributeManager
    ATTR_TABLE:
      REMOVE _clipped (char(3))
      REMOVE _overlaps (uint32)
      RENAME_SET_VALUE min_debiet > min_flow_threshold (varchar(200))
      REMOVE bottom (varchar(200))
      REMOVE fid (varchar(200))
      REMOVE gridcode (varchar(200))
      REMOVE Id (varchar(200))
      REMOVE layer (varchar(200))
      REMOVE left (varchar(200))
      REMOVE max_debiet (varchar(200))
      REMOVE multi_reader_full_id (varchar(200))
      REMOVE multi_reader_id (varchar(200))
      REMOVE multi_reader_keyword (varchar(200))
      REMOVE multi_reader_keyword (varchar(200))
      REMOVE multi_reader_type (varchar(200))
      REMOVE OBJECTID (varchar(200))
      REMOVE ORIG_FID (varchar(200))
      REMOVE path (varchar(200))
      REMOVE Q__clipped (varchar(200))
      REMOVE Resultaat (varchar(200))
      REMOVE right (varchar(200))
      REMOVE scid (varchar(200))
      REMOVE Shape_Area (varchar(200))
      REMOVE Shape_Leng (varchar(200))
      REMOVE shapefile_type (varchar(200))
      REMOVE top (varchar(200))
    USER_EXPOSED_ATTRIBUTES = min_debiet,tid,bottom,fid,gridcode,Id,layer,left,max_debiet,multi_reader_full_id,multi_reader_id,multi_reader_keyword,multi_reader_type,OBJECTID,ORIG_FID,path,Q__clipped,Resultaat,right,scid,Shape_Area,Shape_Leng,shapefile_type,top
    -> min_flow_threshold (output)

Bookmark: Notes on feature
Note: This feature takes the lower bound of each debiet layer, and associates it with the closest tile. Thus for each tile we know approximately when it begins to co-flow. / If this eventually becomes a feature that is update more frequently (yearly) then it should be moved to the tile_observation table instead.

FME custom transformer Aspect
This feature calculates the aspect of the bathymetric data. Important to note is that the data is first aggregated, and then calculated. This captures the high level behavior better than calculating before resampling
This is a dynamic feature, and should be updated yearly

Parameters:
- RIGHT = @Value(right)   # right
- TID = @Value(tid)   # tid
- LEFT = @Value(left)   # left
- BOTTOM = @Value(bottom)   # bottom
- TOP = @Value(top)   # top
- FME_BASENAME = @Value(fme_basename)   # Fme Basename

bathymetry_input (input)
    -> RasterResampler
Note: Already written to DB: / 2024 / 2025
aspect (output)

Bookmark: Aspect Resampled before calculation
RasterResampler
    INTERPOLATION_TYPE = Average16
    ROWCOL_OR_CELLSIZE = CellSize
    X_CELL_SIZE = 2.5
    Y_CELL_SIZE = 2.5
    INTERPOLATION_TYPE_NAME = Average 16
    RESAMPLED -> RasterResampler_2
RasterResampler_2
    INTERPOLATION_TYPE = Average4
    ROWCOL_OR_CELLSIZE = CellSize
    X_CELL_SIZE = 5
    Y_CELL_SIZE = 5
    INTERPOLATION_TYPE_NAME = Average 4
    RESAMPLED -> RasterAspectCalculator

Bookmark: Aspect
RasterAspectCalculator
    ALGORITHM_LOOKUP = ZevenbergenThorne
    INTERPOLATE_NODATA_LOOKUP = InterpolateNodata
    ALGORITHM = Zevenbergen and Thorne
    INTERPOLATE_NODATA = Yes
    -> Clipper_2 [CANDIDATE]
channel_polygon_input (input)
    -> Clipper_2 [CLIPPER]
RasterCellCoercer_3
    CELL_GEOMETRY = Points
    EXTRACT_NODATA = No
    EXTRACT_VALUES_AS_ATTRIBUTES = Yes
    PRESERVE_ATT = YES
    CELL_GEOMETRY_LOOKUP = Points
    EXTRACT_BAND_VALUES_AS = Attributes
    EXTRACT_NODATA_LOOKUP = No
    PRESERVE_ATTRIBUTES = Yes
    -> PointOnAreaOverlayer_5 [POINT]
tile_input (input)
    -> PointOnAreaOverlayer_5 [AREA]
PointOnAreaOverlayer_5
    ATTR_ACCUM_MODE = HANDLE_CONFLICT
    ATTR_CONFLICT_RES = ORIGINAL_IF_CONFLICT
    DEAGGREGATE_INPUT = Yes
    OV_ATTR = _overlaps
    POLYS_FIRST = NO
    POINT -> StatisticsCalculator_4
StatisticsCalculator_4
    ATTR_ACCUM_MODE = All
    CALCULATION_MODE = NUMERIC
    FEAT_STATS = _band{0}.value,NUMERIC_MODE,,,,,MEAN,,,,,,,,
    GROUP_BY = tid
    SUMMARY -> RemoveData_outside_of_tiles_5
RemoveData_outside_of_tiles_5: Tester
    BOOL_OP = OR
    TEST_CLAUSE = TEST tid NOT_ATTRIBUTE_IS_MISSING ""
    TEST_MODE = TEST
    PASSED -> Rename_Attrubute_3
Rename_Attrubute_3: AttributeManager
    ATTR_TABLE:
      RENAME_SET_VALUE _band{0}.value.mean > aspect (real64)
      REMOVE fme_basename (buffer)
      REMOVE _clipped (char(3))
      REMOVE _band{}.min (buffer)
      REMOVE _band{}.max (real64)
      REMOVE _band{}.palette{}.keyMin (buffer)
      REMOVE _band{}.palette{}.keyMax (buffer)
      REMOVE _band{}.palette{}.valueMin (real64)
      REMOVE _band{}.palette{}.valueMax (real64)
      REMOVE _band{}.value (real64)
      REMOVE _band{}.palette{}.value (real64)
      REMOVE left (int64)
      REMOVE top (int64)
      REMOVE right (int64)
      REMOVE bottom (int64)
      REMOVE _overlaps (uint32)
    USER_EXPOSED_ATTRIBUTES = gid,_band{}.value.mean,_band{0}.value.mean,scid
    -> Round_Attribute_5
Round_Attribute_5: AttributeRounder
    PLACES = 4
    ROUND_TYPE_TCL = round
    SRC_ATTRS = aspect
    ROUND_TYPE = Nearest
    -> aspect (output)

Bookmark: Clip and filter
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterBandMinMaxExtractor_4
RasterBandMinMaxExtractor_4
    -> filter_nodata_4
filter_nodata_4: Tester
    BOOL_OP = COMPOSITE
    COMPOSITE_TEST = 1 AND 2
    TEST_CLAUSE:
      TEST @Value(_band{0}.max) NOT_= 9999
      TEST @Value(_band{0}.min) NOT_= 9999
    TEST_MODE = TEST
    PASSED -> RasterCellCoercer_3

Bookmark: Notes on feature
Note: This feature calculates the aspect of the bathymetric data. Important to note is that the data is first aggregated, and then calculated. This captures the high level behavior better than calculating before resampling / This is a dynamic feature, and should be updated yearly

FME custom transformer Channel Length and Relative Length
This feature represents calculates the lengths of the side channel, calculated by taking the distance between a channel's inlet and outlet via the centerline of the polygon. This centerline represents the medial axis transform spine of the polygon. 
For channels that do not have a valid path via the centerline, the euclidian distance between the inlet and outlet is used.
It also includes the relative channel length as output, which is the length of the centerline of the channel relative to the straightline distance from inlet to outlet. This encodes a bit how 'straight' or 'bendy' the side channel is.
This is a static feature (does not update). If this eventually becomes a feature that is update more frequently (yearly) then it should be moved to the observations table instead.

Parameters:
- SEGMENT_ATTRIBUTES_0_.SCID = @Value(segment attributes{0}.scid)   # segment attributes{0}.scid
- OBJECTNAME = @Value(objectname)   # objectname
- SCID = @Value(scid)   # scid

channel_polygon_input (input)
    -> Reprojector_3
inlet_outlet_input (input)
    -> Inlet
    -> outlet
Note: Already written to DB
channel_length (output)
Note: Already written to DB
relative_channel_length (output)

Bookmark: Medial Axis Transform
Reprojector_3
    DEST = Amersfoort-RDNew
    INTERPOLATION_TYPE = NearestNeighbor
    RASTER_CELL_SIZE = PreserveCells
    RASTER_TOLERANCE = 0.0
    REPROJECTED -> CenterlineReplacer
CenterlineReplacer
    MODE = APPROX_CENTER_LINE
    CENTERLINE -> NeighborFinder [CANDIDATE]
    CENTERLINE -> NeighborFinder_2 [CANDIDATE]
    CENTERLINE -> Deaggregator_3

Bookmark: Create chopped mini lines
Deaggregator_3
    ATTR_ACCUM_MODE = HANDLE_CONFLICT
    ATTR_CONFLICT_RES = INCOMING_IF_CONFLICT
    EXPLODE_INSTANCES = Yes
    GEOM_LABEL_FIELD = _geometry_label
    LIST_ATTR_MODE_LOOKUP = LEAN
    PART_NUMBER_FIELD = _part_number
    RECURSIVE = No
    SPLIT_COMPOSITES = Yes
    DEAGGREGATED -> Chopper
Chopper
    DEAGGREGATE_INPUT = Deaggregate
    MAX_VERTICES = 2
    MODE_LOOKUP = VERTEX
    REMNANT_ATTR = _remnant
    MODE = By Vertex
    CHOPPED -> ShortestPathFinder [NETWORK]

Bookmark: Inlet
Inlet: Tester
    BOOL_OP = OR
    TEST_CLAUSE = CASE_INSENSITIVE_TEST @Value(objectname) BEGINS_WITH Inlaat
    TEST_MODE = CASE_INSENSITIVE_TEST
    PASSED -> NeighborFinder [BASE]

Bookmark: Create Inlet/Outlet lines
NeighborFinder
    CANDIDATES_FIRST = No
    INSERT_VERTEX = No
    K = 1
    MEASURES_FROM_CANDIDATE = Yes
    MEASURE_TYPE = Continuous
    MODE = Bases and Candidates
    TREAT_POLYGON_AS = Lines
    MATCHED -> VertexCreator_3
VertexCreator_3
    MEASURE_TYPE_LOOKUP = CONTINUOUS
    MODE = REPLACE
    REMOVE_ATTRIBUTES = No
    XVAL = @Value(_closest_candidate_x)
    YVAL = @Value(_closest_candidate_y)
    MEASURE_TYPE = Continuous
    MODE_NAME = Replace with Point
    -> LineBuilder
NeighborFinder_2
    CANDIDATES_FIRST = No
    INSERT_VERTEX = No
    K = 1
    MEASURES_FROM_CANDIDATE = Yes
    MEASURE_TYPE = Continuous
    MODE = Bases and Candidates
    TREAT_POLYGON_AS = Lines
    MATCHED -> VertexCreator_4
VertexCreator_4
    MEASURE_TYPE_LOOKUP = CONTINUOUS
    MODE = REPLACE
    REMOVE_ATTRIBUTES = No
    XVAL = @Value(_closest_candidate_x)
    YVAL = @Value(_closest_candidate_y)
    MEASURE_TYPE = Continuous
    MODE_NAME = Replace with Point
    -> LineBuilder
LineBuilder
    ACCUM_INPUT_ATTRS_LOOKUP = One
    GROUP_BY = scid
    REMOVE_DUPLICATES_LOOKUP = NO
    ACCUM_INPUT_ATTRS = Use Attributes From One Feature
    REMOVE_DUPLICATES = No
    LINE -> ShortestPathFinder [FROM-TO]
    LINE -> LengthCalculator_2

Bookmark: Outlet
outlet: Tester
    BOOL_OP = OR
    TEST_CLAUSE = CASE_INSENSITIVE_TEST @Value(objectname) BEGINS_WITH Uitlaat
    TEST_MODE = CASE_INSENSITIVE_TEST
    PASSED -> NeighborFinder_2 [BASE]

Bookmark: Find Shortest Paths
ShortestPathFinder
    ALLOW_UTURNS = Yes
    GROUP_BY = scid
    REORDER_MODE = NONE
    SNAP_POINTS = Yes
    SNAP_TOLERANCE = 200
    THREE_D = No
    WEIGHT_ATTR_CHOICE = BY_LENGTH
    PATH -> Tester
    NOPATH -> LengthCalculator
Tester
    BOOL_OP = OR
    TEST_CLAUSE = TEST _total_cost ATTRIBUTE_IS_MISSING ""
    TEST_MODE = TEST
    FAILED -> AttributeManager_2
AttributeManager_2
    ATTR_TABLE:
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      RENAME_SET_VALUE _total_cost > channel_length (buffer)
      REMOVE segment attributes{}.scid (int32)
      REMOVE objectname (varchar(200))
    USER_EXPOSED_ATTRIBUTES = gid,_length,segment attributes{0}.scid
    -> AttributeRounder_2
LengthCalculator
    DIM = 2
    LEN_ATTR = _length
    MULT = 1
    -> Tester_2
Tester_2
    BOOL_OP = OR
    TEST_CLAUSE = TEST _length ATTRIBUTE_IS_MISSING ""
    TEST_MODE = TEST
    FAILED -> AttributeManager
AttributeManager
    ATTR_TABLE:
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      RENAME_SET_VALUE _length > channel_length (real64)
      REMOVE segment attributes{0}.scid (varchar(200))
      REMOVE objectname (varchar(200))
      REMOVE segment attributes{}.scid (varchar(200))
    -> AttributeRounder_2
AttributeRounder_2
    PLACES = 4
    ROUND_TYPE_TCL = round
    SRC_ATTRS = channel_length
    ROUND_TYPE = Nearest
    -> channel_length (output)
    -> FeatureMerger [REQUESTOR]

Bookmark: Find Relative Channel Length
LengthCalculator_2
    DIM = 2
    LEN_ATTR = _length
    MULT = 1
    -> FeatureMerger [SUPPLIER]
FeatureMerger
    ATTR_ACCUM_MODE = Merge Supplier
    ATTR_CONFLICT_RES_LOOKUP = REQUESTOR_IF_CONFLICT
    IGNORE_NULLS = No
    JOIN_KEYS = @Value(scid) @Value(scid) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager_3
AttributeManager_3
    ATTR_TABLE:
      SET_TO relative_channel_length (real64) = @Evaluate(@Value(channel_length)/@Value(_length))
      REMOVE channel_length (buffer)
      REMOVE objectname (varchar(200))
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE _length (real64)
      REMOVE segment attributes{0}.scid (varchar(200))
      REMOVE segment attributes{}.scid (varchar(200))
    -> AttributeRounder_3
AttributeRounder_3
    PLACES = 4
    ROUND_TYPE_TCL = round
    SRC_ATTRS = relative_channel_length
    ROUND_TYPE = Nearest
    -> relative_channel_length (output)

Bookmark: Notes on feature
Note: This feature represents the length of the side channel, calculated by taking the distance between a channel's inlet and outlet via the centerline of the polygon. This centerline represents the medial axis transform spine of the polygon. / For channels that do not have a valid path via the centerline, the euclidian distance between the inlet and outlet is used. / It also includes the relative channel length as output, which is the length of the centerline of the channel relative to the straightline distance from inlet to outlet. This encodes a bit how 'straight' or 'bendy' the side channel is. / This is a static feature (does not update). If this eventually becomes a feature that is update more frequently (yearly) then it should be moved to the observations table instead.

FME custom transformer Slope
This feature calculates the slope of the bathymetric data, then writes the average value aggregated over the 5x5m area
This is a dynamic feature, and should be updated yearly

Parameters:
- RIGHT = @Value(right)   # right
- TID = @Value(tid)   # tid
- LEFT = @Value(left)   # left
- BOTTOM = @Value(bottom)   # bottom
- TOP = @Value(top)   # top
- FME_BASENAME = @Value(fme_basename)   # Fme Basename

channel_polygon_input (input)
    -> clipped_to_polygon_3 [CLIPPER]
bathymetry_input (input)
    -> RasterSlopeCalculator
Note: Already written to DB: / 2024 / 2025
slope (output)

Bookmark: Slope
RasterSlopeCalculator
    ALGORITHM_LOOKUP = ZevenbergenThorne
    INTERPOLATE_NODATA_LOOKUP = InterpolateNodata
    OUTPUT_TYPE_LOOKUP = Degrees
    ALGORITHM = Zevenbergen and Thorne
    INTERPOLATE_NODATA = Yes
    OUTPUT_TYPE = Degrees
    -> clipped_to_polygon_3 [CANDIDATE]
RasterCellCoercer_2
    CELL_GEOMETRY = Points
    EXTRACT_NODATA = No
    EXTRACT_VALUES_AS_ATTRIBUTES = Yes
    PRESERVE_ATT = YES
    CELL_GEOMETRY_LOOKUP = Points
    EXTRACT_BAND_VALUES_AS = Attributes
    EXTRACT_NODATA_LOOKUP = No
    PRESERVE_ATTRIBUTES = Yes
    -> PointOnAreaOverlayer_4 [POINT]
tile_input (input)
    -> PointOnAreaOverlayer_4 [AREA]
PointOnAreaOverlayer_4
    ATTR_ACCUM_MODE = HANDLE_CONFLICT
    ATTR_CONFLICT_RES = ORIGINAL_IF_CONFLICT
    DEAGGREGATE_INPUT = Yes
    OV_ATTR = _overlaps
    POLYS_FIRST = NO
    POINT -> StatisticsCalculator_3
StatisticsCalculator_3
    ATTR_ACCUM_MODE = All
    CALCULATION_MODE = NUMERIC
    FEAT_STATS = _band{0}.value,NUMERIC_MODE,,,,,MEAN,,,,,,,,
    GROUP_BY = tid
    SUMMARY -> RemoveData_outside_of_tiles_4
RemoveData_outside_of_tiles_4: Tester
    BOOL_OP = OR
    TEST_CLAUSE = TEST tid NOT_ATTRIBUTE_IS_MISSING ""
    TEST_MODE = TEST
    PASSED -> Rename_Attrubute_4
Rename_Attrubute_4: AttributeManager
    ATTR_TABLE:
      RENAME_SET_VALUE _band{0}.value.mean > slope (real64)
      REMOVE _band{}.value.mean (varchar(200))
      REMOVE fme_basename (buffer)
      REMOVE _clipped (char(3))
      REMOVE _band{}.min (buffer)
      REMOVE _band{}.max (real64)
      REMOVE _band{}.palette{}.keyMin (buffer)
      REMOVE _band{}.palette{}.keyMax (buffer)
      REMOVE _band{}.palette{}.valueMin (real64)
      REMOVE _band{}.palette{}.valueMax (real64)
      REMOVE _band{}.value (real64)
      REMOVE _band{}.palette{}.value (real64)
      REMOVE left (int64)
      REMOVE top (int64)
      REMOVE right (int64)
      REMOVE bottom (int64)
      REMOVE _overlaps (uint32)
    USER_EXPOSED_ATTRIBUTES = gid,scid
    -> Round_Attribute_4
Round_Attribute_4: AttributeRounder
    PLACES = 4
    ROUND_TYPE_TCL = round
    SRC_ATTRS = slope
    ROUND_TYPE = Nearest
    -> slope (output)

Bookmark: Clipped Slope
clipped_to_polygon_3: Clipper
    ADD_NODATA = NO
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterBandMinMaxExtractor_3
RasterBandMinMaxExtractor_3
    -> filter_nodata_3
filter_nodata_3: Tester
    BOOL_OP = COMPOSITE
    COMPOSITE_TEST = 1 AND 2
    TEST_CLAUSE:
      TEST @Value(_band{0}.max) NOT_= 9999
      TEST @Value(_band{0}.min) NOT_= 9999
    TEST_MODE = TEST
    PASSED -> RasterCellCoercer_2

Bookmark: Notes on feature
Note: This feature calculates the slope of the bathymetric data, then writes the average value aggregated over the 5x5m area / This is a dynamic feature, and should be updated yearly

FME custom transformer Distance to Bank
This feature represents a tile's distance from the bank of the channel. This will encode for each channel relatively where in the channel the tile sits, as more central tiles tend to behave differently than those near banks

Parameters:
- BOTTOM = @Value(bottom)   # bottom
- SCID = @Value(scid)   # scid
- RIGHT = @Value(right)   # right
- TOP = @Value(top)   # top
- NAME = @Value(name)   # name
- LEFT = @Value(left)   # left

tile_input (input)
    -> CenterPointReplacer
channel_polygon_input (input)
    -> NeighborFinder [CANDIDATE]
distance_to_bank (output)

Bookmark: Determine distance to bank
CenterPointReplacer
    POINTTYPE = CENTER
    POINT -> NeighborFinder [BASE]
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> AttributeManager
AttributeManager
    ATTR_TABLE:
      REMOVE left (int64)
      REMOVE top (int64)
      REMOVE right (int64)
      REMOVE bottom (int64)
      REMOVE scid (int32)
      REMOVE name (varchar(254))
      RENAME_SET_VALUE _distance > distance_to_bank (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
    -> AttributeRounder_2
AttributeRounder_2
    PLACES = 3
    ROUND_TYPE_TCL = round
    SRC_ATTRS = distance_to_bank
    ROUND_TYPE = Nearest
    -> distance_to_bank (output)

Bookmark: Notes on feature
Note: This feature calculates the distance between each tile and the border of the polygon representing the channel. Thus it calculates the distance between the tile and the bank of the channel. / This is a static feature (does not update). If this eventually becomes a feature that is update more frequently (yearly) then it should be moved to the observations table instead.

FME custom transformer Area and Perimeter
This is a very simple feature consisting of the area and perimeter of the polygons representing the side channel geometry

Parameters:
- NAME = @Value(name)   # name
- SCID = @Value(scid)   # scid

channel_polygon_input (input)
    -> LengthCalculator
Note: Already written to DB
perimeter_and_area (output)

Bookmark: Calculate values
LengthCalculator
    DIM = 2
    LEN_ATTR = perimeter
    MULT = 0.001
    -> AreaCalculator
AreaCalculator
    AREA_ATTR = area
    AREA_TYPE = Plane Area
    MULT = 0.001
    -> AttributeManager_3
AttributeManager_3
    USER_EXPOSED_ATTRIBUTES = old_area,old_perimeter
    -> perimeter_and_area (output)

FME custom transformer Width
Calculates width based off of the polygon geometry. Based off of the centerline (medial axis), inserts points along the line, generates perpendicular lines, and uses the length of those lines as an estimation of width at every point in the channel. The nearest neighbor cascading of the width value can lead to strange values in parts of the channel very far from the centerline.

Parameters:
- TOP = @Value(top)   # top
- GROYNEVAK = @Value(groynevak)   # groynevak
- NAME = @Value(name)   # name
- LEFT = @Value(left)   # left
- PERIMETER = @Value(perimeter)   # perimeter
- BOTTOM = @Value(bottom)   # bottom
- RIGHT = @Value(right)   # right
- AREA = @Value(area)   # area
- TID = @Value(tid)   # tid

channel_polygon_input (input)
    -> CenterlineReplacer
    -> Junction
    -> BoundsExtractor
Note: Clipper : Clipper
Junction
    -> Junction_2
tile_input (input)
    -> Clipper_2 [CLIPPER]
    -> Junction_3
Note: PointOnAreaOverlayer_2 : Area
Junction_3
    -> Junction_4
Note: Already written to DB
Width (output)

Bookmark: Azimuth per line segment in 5 x 5m grid
CenterlineReplacer
    MODE = APPROX_CENTER_LINE
    CENTERLINE -> Generalizer
Generalizer
    ALG = Douglas
    PRESERVE = No
    PRESERVE_PATHS_LOOKUP = NO
    TOLERANCE = 3
    ALG_TEXT = Douglas (Generalize)
    PRESERVE_PATHS = No
    -> Clipper_2 [CANDIDATE]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> CoordinateExtractor
CoordinateExtractor
    LIST_NAME = _indices
    RECURSIVE = Yes
    MODE = All Coordinates
    -> HorizontalAngleCalculator
HorizontalAngleCalculator
    ANGLE_TYPE = Feature
    UNIT_OUTPUT = DEG
    -> AttributeManager_2
    <Rejected> -> Junction_8
Junction_8

Bookmark: compute width
Note: channel_polygon_input
Junction_2
    -> Clipper [CLIPPER]
AttributeManager_2
    ATTR_TABLE:
      SET_TO Last_element (real64) = @Evaluate(@NumCoords()-2)
      SET_TO x_mid (real64) = @Evaluate((@Value(_indices{0}.x)+@Value(_indices{@Value(Last_element)}.x))/2)
      SET_TO y_mid (real64) = @Evaluate((@Value(_indices{0}.y)+@Value(_indices{@Value(Last_element)}.y))/2)
      SET_TO x_perpendicular (real64) = @Evaluate(@Value(x_mid)+5*@cos(@Value(_azimuth)*@pi()/180))
      SET_TO y_perpendicular (real64) = @Evaluate(@Value(y_mid)-5*@sin(@Value(_azimuth)*@pi()/180))
      SET_TO join_id (real64) = @Evaluate(1)
    -> FeatureMerger_2 [REQUESTOR]
FeatureMerger_2
    ATTR_ACCUM_MODE = Merge Supplier
    ATTR_CONFLICT_RES_LOOKUP = REQUESTOR_IF_CONFLICT
    IGNORE_NULLS = No
    JOIN_KEYS = @Value(join_id) @Value(join_id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Counter
    <REJECTED> -> Junction_11
Counter
    CNT_ATTR = _count
    DOMAIN = counter
    SCOPE = Global
    START = 0
    -> VertexCreator
VertexCreator
    MEASURE_TYPE_LOOKUP = CONTINUOUS
    MODE = REPLACE
    REMOVE_ATTRIBUTES = No
    XVAL = (@Value(_indices{0}.x)+@Value(_indices{@Value(Last_element)}.x))/2
    YVAL = (@Value(_indices{0}.y)+@Value(_indices{@Value(Last_element)}.y))/2
    MEASURE_TYPE = Continuous
    MODE_NAME = Replace with Point
    -> VertexCreator_2
    <REJECTED> -> Junction_5
Junction_5
    -> Junction_6
VertexCreator_2
    ALLOW_DUPLICATES = NO
    CLOSE_LINES = Yes
    MEASURE_TYPE_LOOKUP = CONTINUOUS
    MISSING_VAL_MODE_LOOKUP = COMPUTE_NANS
    MODE = ADD
    REMOVE_ATTRIBUTES = No
    XVAL = @Value(x_perpendicular)
    YVAL = @Value(y_perpendicular)
    IGNORE_DUPLICATES = Yes
    MEASURE_TYPE = Continuous
    MISSING_VAL_MODE = Compute
    MODE_NAME = Add Point
    -> LineExtender
LineExtender
    LEN = @Value(line_extend_length)
    STRETCHED -> Clipper [CANDIDATE]
    <REJECTED> -> Junction_7
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator_2
    <REJECTED> -> Junction_9
Deaggregator_2
    ATTR_ACCUM_MODE = HANDLE_CONFLICT
    ATTR_CONFLICT_RES = INCOMING_IF_CONFLICT
    EXPLODE_INSTANCES = No
    GEOM_LABEL_FIELD = _geometry_label
    LIST_ATTR = _indices{}
    LIST_ATTR_MODE_LOOKUP = LEAN
    PART_NUMBER_FIELD = _part_number
    RECURSIVE = No
    SPLIT_COMPOSITES = No
    DEAGGREGATED -> LengthCalculator_2
LengthCalculator_2
    DIM = 2
    LEN_ATTR = _length
    MULT = 1
    -> BoundsExtractor_3
Junction_9
    -> Junction_6
Junction_7
    -> Junction_6
Junction_11
    -> Junction_6
Note: The trashcan
Junction_6

Bookmark: compute bbox length
BoundsExtractor
    XMAX = _xmax
    XMIN = _xmin
    YMAX = _ymax
    YMIN = _ymin
    ZMAX = _zmax
    ZMIN = _zmin
    -> AttributeManager_3
AttributeManager_3
    ATTR_TABLE:
      REMOVE scid (int32)
      REMOVE name (varchar(254))
      REMOVE area (number(1000,500))
      REMOVE perimeter (number(1000,500))
      REMOVE _zmin (real64)
      REMOVE _zmax (real64)
      SET_TO x_width_bbox (real64) = @Evaluate((@Value(_xmax)-@Value(_xmin))*2)
      SET_TO y_width_bbox (real64) = @Evaluate((@Value(_ymax)-@Value(_ymin))*2)
      SET_TO line_extend_length (real64) = FME_CONDITIONAL:DEFAULT_VALUE'@Value(y_width_bbox)'BOOL_OP;OR;COMPOSITE_TEST;1;TEST @Value(x_width_bbox) >= @Value(y_width_bbox)'@Value(x_width_bbox)'FME_NUM_CONDITIONS2___
      SET_TO join_id (real64) = @Evaluate(1)
    -> FeatureMerger_2 [SUPPLIER]

Bookmark: Postprocess, give width value to tiles
Junction_4
    -> PointOnAreaOverlayer_2 [AREA]
BoundsExtractor_3
    XMAX = _xmax
    XMIN = _xmin
    YMAX = _ymax
    YMIN = _ymin
    ZMAX = _zmax
    ZMIN = _zmin
    -> VertexCreator_4
VertexCreator_4
    MEASURE_TYPE_LOOKUP = CONTINUOUS
    MODE = REPLACE
    REMOVE_ATTRIBUTES = No
    XVAL = @Value(x_mid)
    YVAL = @Value(y_mid)
    MEASURE_TYPE = Continuous
    MODE_NAME = Replace with Point
    -> Tester_2
Tester_2
    BOOL_OP = AND
    TEST_CLAUSE:
      TEST @Value(x_mid) < @Value(_xmax)
      TEST @Value(x_mid) > @Value(_xmin)
      TEST @Value(y_mid) < @Value(_ymax)
      TEST @Value(y_mid) > @Value(_ymin)
    TEST_MODE = TEST
    PASSED -> To_many_attributes
To_many_attributes: AttributeManager
    ATTR_TABLE:
      REMOVE join_id (real64)
      REMOVE name (varchar(254))
      REMOVE area (number(1000,500))
      REMOVE perimeter (number(1000,500))
      REMOVE _clipped (char(3))
      REMOVE _part_number (uint64)
      REMOVE _geometry_label (buffer)
      REMOVE Last_element (real64)
      REMOVE _azimuth (real64)
      REMOVE _X (real64)
      REMOVE _Y (real64)
      REMOVE _angle (real64)
      REMOVE fme_rejection_code (varchar(200))
      REMOVE _creation_instance (varchar(200))
      REMOVE _x (varchar(200))
      REMOVE _y (varchar(200))
      REMOVE _z (varchar(200))
      REMOVE _xEnd (varchar(200))
      REMOVE _yEnd (varchar(200))
      REMOVE _zEnd (varchar(200))
      REMOVE x_perpendicular (real64)
      REMOVE y_perpendicular (real64)
      REMOVE _xmin (real64)
      REMOVE _xmax (real64)
      REMOVE _ymin (real64)
      REMOVE _ymax (real64)
      REMOVE x_width_bbox (real64)
      REMOVE y_width_bbox (real64)
      REMOVE line_extend_length (real64)
      RENAME_SET_VALUE _length > width (real64)
      REMOVE _count (int64)
      REMOVE x (real64)
      REMOVE y (real64)
      REMOVE z (real64)
      REMOVE _zmin (real64)
      REMOVE _zmax (real64)
      REMOVE groynevak (logical)
    USER_EXPOSED_ATTRIBUTES = top,bottom,scid,inlet_x,inlet_y,_z,section_azimuth,_indices{0}.y,_indices{}.y,_indices{}.z
    -> PointOnAreaOverlayer_2 [POINT]
PointOnAreaOverlayer_2
    ATTR_ACCUM_MODE = HANDLE_CONFLICT
    ATTR_CONFLICT_RES = ORIGINAL_IF_CONFLICT
    DEAGGREGATE_INPUT = Yes
    OV_ATTR = _overlaps
    POLYS_FIRST = NO
    AREA -> Split_tiles_into_if_it_has_a_width_value
Split_tiles_into_if_it_has_a_width_value: Tester
    BOOL_OP = OR
    TEST_CLAUSE = TEST width ATTRIBUTE_IS_MISSING ""
    TEST_MODE = TEST
    PASSED -> Give_empty_tiles_the_nearest_neighbor_value [BASE]
    FAILED -> Tester_4
    FAILED -> Give_empty_tiles_the_nearest_neighbor_value [CANDIDATE]
Give_empty_tiles_the_nearest_neighbor_value: NeighborFinder
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Lines
    MATCHED -> Tester_4

Bookmark: Prepare for DB
Tester_4
    BOOL_OP = OR
    TEST_CLAUSE = TEST tid NOT_ATTRIBUTE_IS_MISSING ""
    TEST_MODE = TEST
    PASSED -> AttributeManager
AttributeManager
    ATTR_TABLE:
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE left (varchar(200))
      REMOVE top (varchar(200))
      REMOVE right (varchar(200))
      REMOVE bottom (varchar(200))
      REMOVE scid (int32)
      REMOVE _overlaps (uint32)
      REMOVE x_mid (real64)
      REMOVE y_mid (real64)
      REMOVE groynevak (varchar(200))
      REMOVE name (varchar(200))
      REMOVE perimeter (varchar(200))
      REMOVE area (varchar(200))
    USER_EXPOSED_ATTRIBUTES = gid,width.mean,tid
    -> AttributeRounder
AttributeRounder
    PLACES = 4
    ROUND_TYPE_TCL = round
    SRC_ATTRS = width
    ROUND_TYPE = Nearest
    -> Width (output)

Bookmark: Notes on feature
Note: This feature calculates the width of the side channel. This is derived by calculating a centerline through the side channel polygons, and then chopping it into small sections. For each section, perpendicular lines are drawn outwards, which are then clipped by the channel polygon. The segments are de-aggregated, and then the tiles are given the closest width value based off of the length of these perpendicular line segments. / For tiles that are not directly intersected by one of these perpendicular lines, they recieve the value of their nearest neighbor. / This is a static feature (does not update). If this eventually becomes a feature that is update more frequently (yearly) then it should be moved to the observations table instead.

Bookmark: Compute width
Note: tile_input

FME custom transformer Roughness
This feature calculates the roughness, per tile, for each side channel with valid bathymetric data. The equation is based off of a paper (https://doi.org/10.1080/01490410701295962)
This is a dynamic feature, and should be updated yearly

Parameters:
- RIGHT = @Value(right)   # right
- TID = @Value(tid)   # tid
- LEFT = @Value(left)   # left
- BOTTOM = @Value(bottom)   # bottom
- TOP = @Value(top)   # top
- FME_BASENAME = @Value(fme_basename)   # Fme Basename

bathymetry_input (input)
    -> Min
    -> Max
Note: Already written to DB: / 2024 / 2025
roughness (output)

Bookmark: Caclulate Roughness
Min: RasterConvolver
    CENTER_PIXEL_NODATA_HANDLING = OutputNodata
    CONVOLUTION_FILTER = UserDefined
    EDGE_HANDLING = UseNodataOutsideRaster
    KERNEL_DIVISOR = Sum of Kernel Weights
    KERNEL_OPERATION = Minimum
    KERNEL_WEIGHTS = 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1
    NEIGHBOR_PIXEL_NODATA_HANDLING = UseCenterPixel
    PRESERVE_BAND_INTERPRETATION = No
    ZERO_WEIGHT_HANDLING = IgnoreZeroWeightValues
    -> AttributeManager
AttributeManager
    ATTR_TABLE = SET_TO order (uint8) = 0
    USER_EXPOSED_ATTRIBUTES = order
    -> Sorter
Max: RasterConvolver
    CENTER_PIXEL_NODATA_HANDLING = OutputNodata
    CONVOLUTION_FILTER = UserDefined
    EDGE_HANDLING = UseNodataOutsideRaster
    KERNEL_DIVISOR = Sum of Kernel Weights
    KERNEL_OPERATION = Maximum
    KERNEL_WEIGHTS = 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1 1
    NEIGHBOR_PIXEL_NODATA_HANDLING = UseCenterPixel
    PRESERVE_BAND_INTERPRETATION = No
    ZERO_WEIGHT_HANDLING = IgnoreZeroWeightValues
    -> AttributeManager_2
AttributeManager_2
    ATTR_TABLE = SET_TO order (uint8) = 1
    USER_EXPOSED_ATTRIBUTES = order
    -> Sorter
Sorter
    SORT_PARM = order NUMERIC ASCENDING NON_VALUES_AFTER_VALUES
    SORTED -> RasterBandCombiner
RasterBandCombiner
    ACCUM_ATTRS_LOOKUP = ONE
    GROUP_BY = fme_basename
    ACCUM_ATTRS = Use Attributes From One Feature
    -> RasterExpressionEvaluator [A]
RasterExpressionEvaluator
    EXPRESSION_LIST = PRESERVE A[1]-A[0]
    MODE = One Raster
    RESULT -> clipped_to_polygon [CANDIDATE]

Bookmark: Roughness
channel_polygon_input (input)
    -> clipped_to_polygon [CLIPPER]

Bookmark: Clip to polygon
clipped_to_polygon: Clipper
    ADD_NODATA = NO
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterBandMinMaxExtractor_2
RasterBandMinMaxExtractor_2
    -> filter_nodata
filter_nodata: Tester
    BOOL_OP = COMPOSITE
    COMPOSITE_TEST = 1 AND 2
    TEST_CLAUSE:
      TEST @Value(_band{0}.max) NOT_= 9999
      TEST @Value(_band{0}.min) NOT_= 9999
    TEST_MODE = TEST
    PASSED -> RasterCellCoercer

Bookmark: Encode
RasterCellCoercer
    CELL_GEOMETRY = Points
    EXTRACT_NODATA = No
    EXTRACT_VALUES_AS_ATTRIBUTES = Yes
    PRESERVE_ATT = YES
    CELL_GEOMETRY_LOOKUP = Points
    EXTRACT_BAND_VALUES_AS = Attributes
    EXTRACT_NODATA_LOOKUP = No
    PRESERVE_ATTRIBUTES = Yes
    -> PointOnAreaOverlayer [POINT]
tile_input (input)
    -> PointOnAreaOverlayer [AREA]
PointOnAreaOverlayer
    ATTR_ACCUM_MODE = HANDLE_CONFLICT
    ATTR_CONFLICT_RES = ORIGINAL_IF_CONFLICT
    DEAGGREGATE_INPUT = Yes
    OV_ATTR = _overlaps
    POLYS_FIRST = NO
    POINT -> StatisticsCalculator
StatisticsCalculator
    ATTR_ACCUM_MODE = All
    CALCULATION_MODE = NUMERIC
    FEAT_STATS = _band{0}.value,NUMERIC_MODE,,,,,MEAN,,,,,,,,
    GROUP_BY = tid
    SUMMARY -> RemoveData_outside_of_tiles_3
RemoveData_outside_of_tiles_3: Tester
    BOOL_OP = OR
    TEST_CLAUSE = TEST tid NOT_ATTRIBUTE_IS_MISSING ""
    TEST_MODE = TEST
    PASSED -> Rename_Attrubute_2
Rename_Attrubute_2: AttributeManager
    ATTR_TABLE:
      RENAME_SET_VALUE _band{0}.value.mean > roughness (real64)
      REMOVE _band{}.value.mean (varchar(200))
      REMOVE fme_basename (buffer)
      REMOVE order (uint8)
      REMOVE _clipped (char(3))
      REMOVE _band{}.min (buffer)
      REMOVE _band{}.max (real64)
      REMOVE _band{}.palette{}.keyMin (buffer)
      REMOVE _band{}.palette{}.keyMax (buffer)
      REMOVE _band{}.palette{}.valueMin (real64)
      REMOVE _band{}.palette{}.valueMax (real64)
      REMOVE _band{}.value (real64)
      REMOVE _band{}.palette{}.value (real64)
      REMOVE left (int64)
      REMOVE top (int64)
      REMOVE right (int64)
      REMOVE bottom (int64)
      REMOVE _overlaps (uint32)
    USER_EXPOSED_ATTRIBUTES = gid,scid
    -> Round_Attribute_3
Round_Attribute_3: AttributeRounder
    PLACES = 4
    ROUND_TYPE_TCL = round
    SRC_ATTRS = roughness
    ROUND_TYPE = Nearest
    -> roughness (output)

Bookmark: Notes on feature
Note: This feature calculates the roughness, per tile, for each side channel with valid bathymetric data. The equation is based off of a paper (https://doi.org/10.1080/01490410701295962) / This is a dynamic feature, and should be updated yearly

FME custom transformer Vegetation
This feature represents the approximate vegetation percentage (between 0 and 100)  surrounding a side channel (50m buffer surrounding the side channel polygon). Taken by taking the percentage of 'bos', 'struweel', and 'riet' types from the input vegetation raster.
This is a dynamic feature, and should be updated yearly

Parameters:
- SCID = @Value(scid)   # scid

channel_polygon_input (input)
    -> Bufferer
vegetation_raster_input (input)
    -> Reprojector
Note: Already written to DB: / 2024 / 2025 not written as data is not done being collected
vegetation_percentage (output)

Bookmark: Prepare polygons
Bufferer
    ANGLE = 22.5
    CAP_STYLE_LOOKUP = CAP_ARC
    CORNER_STYLE_LOOKUP = JOIN_ARC
    MODE = AREA
    OFFSET = 100
    OFFSET_UNITS = NONE
    PRECISION = APPROX
    CAP_STYLE = Arc
    CORNER_STYLE = Arc
    BUFFERED -> Clipper [CLIPPER]
    BUFFERED -> SpatialFilter [Filter]

Bookmark: Prepare raster
Reprojector
    DEST = Amersfoort-RDNew
    INTERPOLATION_TYPE = Bilinear
    RASTER_CELL_SIZE = PreserveCells
    RASTER_TOLERANCE = 0.0
    REPROJECTED -> RasterBandNodataSetter
RasterBandNodataSetter
    NODATA_VALUE = 0
    REPLACE_CELL_VALUES_LOOKUP = DoNotReplaceCellValues
    REPLACE_CELL_VALUES = No
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterCellCoercer

Bookmark: Raster to points
RasterCellCoercer
    CELL_GEOMETRY = Points
    EXTRACT_NODATA = No
    EXTRACT_VALUES_AS_ATTRIBUTES = Yes
    PRESERVE_ATT = NO
    CELL_GEOMETRY_LOOKUP = Points
    EXTRACT_BAND_VALUES_AS = Attributes
    EXTRACT_NODATA_LOOKUP = No
    PRESERVE_ATTRIBUTES = No
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = CONTAINS
    USE_BOUNDING_BOX = No
    PASSED -> StatisticsCalculator_3
    PASSED -> Tester_2

Bookmark: Total
StatisticsCalculator_3
    ATTR_ACCUM_MODE = None
    CALCULATION_MODE = NUMERIC
    FEAT_STATS = _band{0}.value,NUMERIC_MODE,,,,,,,,VALUE_COUNT,,,,,
    GROUP_BY = scid
    SUMMARY -> AttributeRenamer_2
AttributeRenamer_2
    ATTR_TABLE = RENAME_SET_DEFAULT _band{0}.value.value_count > total
    KEEP_RENAMED_ONLY = no
    MISSING_INPUT_ATTRS = REMOVE
    -> FeatureMerger [REQUESTOR]

Bookmark: Vegetation
Tester_2
    BOOL_OP = AND
    TEST_CLAUSE:
      TEST @Value(_band{0}.value) NOT_= 2
      TEST @Value(_band{0}.value) NOT_= 1
    TEST_MODE = TEST
    PASSED -> StatisticsCalculator
StatisticsCalculator
    ATTR_ACCUM_MODE = None
    CALCULATION_MODE = NUMERIC
    FEAT_STATS = _band{0}.value,NUMERIC_MODE,,,,,,,,VALUE_COUNT,,,,,
    GROUP_BY = scid
    SUMMARY -> AttributeRenamer
AttributeRenamer
    ATTR_TABLE = RENAME_SET_DEFAULT _band{0}.value.value_count > vegetation
    KEEP_RENAMED_ONLY = no
    MISSING_INPUT_ATTRS = REMOVE
    -> FeatureMerger [SUPPLIER]

Bookmark: Calculate grass percentage
FeatureMerger
    ATTR_ACCUM_MODE = Merge Supplier
    ATTR_CONFLICT_RES_LOOKUP = REQUESTOR_IF_CONFLICT
    IGNORE_NULLS = No
    JOIN_KEYS = @Value(scid) @Value(scid) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeManager
AttributeManager
    ATTR_TABLE:
      SET_TO vegetation_percentage (real64) = @Evaluate((@Value(vegetation) / @Value(total)) * 100)
      REMOVE total (real64)
      REMOVE vegetation (real64)
    -> Round_Attribute_2
Round_Attribute_2: AttributeRounder
    PLACES = 4
    ROUND_TYPE_TCL = round
    SRC_ATTRS = vegetation_percentage
    ROUND_TYPE = Nearest
    -> vegetation_percentage (output)

Bookmark: Notes on feature
Note: This feature represents the approximate vegetation percentage surrounding a side channel. Taken by taking the percentage of 'bos', 'struweel', and 'riet' types from the input vegetation raster. / This is a dynamic feature, and should be updated yearly

FME custom transformer Flow Direction
Transformer for flow direction

Parameters:
- OBJECTMANA = @Value(objectmana)   # objectmana
- OBJECTNAME = @Value(objectname)   # objectname
- OBJECTID = @Value(objectid)   # objectid
- RIGHT = @Value(right)   # right
- FAULTCOUNT = @Value(faultcount)   # faultcount
- RISKLEVEL = @Value(risklevel)   # risklevel
- TYPEID = @Value(typeid)   # typeid
- OBJECTLONG = @Value(objectlong)   # objectlong
- LINKEDCOMP = @Value(linkedcomp)   # linkedcomp
- TYPENAME = @Value(typename)   # typename
- SCID = @Value(scid)   # scid
- OBJECTOWNE = @Value(objectowne)   # objectowne
- YEAROF_CON = @Value(yearof_con)   # Yearof Con
- NAME = @Value(name)   # name
- ULTIMOURL = @Value(ultimourl)   # ultimourl
- LEFT = @Value(left)   # left
- OBJECTCOND = @Value(objectcond)   # objectcond
- RISKSCORE = @Value(riskscore)   # riskscore
- OBJECTLATI = @Value(objectlati)   # objectlati
- TIMESTAMP = @Value(timestamp)   # timestamp

inlet_outlet_points (input)
    -> Reprojector_3
channel_polygon_input (input)
    -> NeighborFinder_3 [CANDIDATE]
    -> Junction_3
Junction_3
    -> Junction_4
Note: Already written to DB
flow_direction (output)

Bookmark: Get Inlet and Outlet
Reprojector_3
    DEST = Amersfoort-RDNew
    INTERPOLATION_TYPE = NearestNeighbor
    RASTER_CELL_SIZE = PreserveCells
    RASTER_TOLERANCE = 0.0
    REPROJECTED -> NeighborFinder_3 [BASE]
NeighborFinder_3
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> VertexCreator_7
VertexCreator_7
    MEASURE_TYPE_LOOKUP = CONTINUOUS
    MODE = REPLACE
    REMOVE_ATTRIBUTES = No
    XVAL = @Value(_closest_base_x)
    YVAL = @Value(_closest_base_y)
    MEASURE_TYPE = Continuous
    MODE_NAME = Replace with Point
    -> Inlet_2
    -> outlet_2

Bookmark: Inlet
Inlet_2: Tester
    BOOL_OP = OR
    TEST_CLAUSE = CASE_INSENSITIVE_TEST @Value(objectname) BEGINS_WITH Inlaat
    TEST_MODE = CASE_INSENSITIVE_TEST
    PASSED -> Inlet_coord

Bookmark: Angle inlet to outlet
Inlet_coord: CoordinateExtractor
    IND = 0
    RECURSIVE = No
    X_ATTR = inlet_x
    Y_ATTR = inlet_y
    Z_ATTR = _z
    MODE = Specify Coordinate
    -> FeatureJoiner_2 [LEFT]
Outlet_coord: CoordinateExtractor
    IND = 0
    RECURSIVE = No
    X_ATTR = outlet_x
    Y_ATTR = outlet_y
    Z_ATTR = _z
    MODE = Specify Coordinate
    -> FeatureJoiner_2 [RIGHT]
FeatureJoiner_2
    ATTR_CONFLICT_RES_LOOKUP = USE_LEFT
    GEOMETRY_HANDLING_LOOKUP = USE_LEFT
    JOIN_KEYS = scid scid AUTO
    JOIN_MODE = Inner
    ATTR_CONFLICT_RES = Prefer Left
    GEOMETRY_HANDLING = Prefer Left
    JOINED -> FeatureJoiner [RIGHT]
    JOINED -> AttributeManager_3
AttributeManager_3
    ATTR_TABLE = SET_TO average_angle (real64) = @Evaluate(360+(@atan2(@Value(outlet_x)-@Value(inlet_x),@Value(outlet_y)-@Value(inlet_y)))*180/@pi())
    USER_EXPOSED_ATTRIBUTES = average_angle
    -> FeatureJoiner_3 [RIGHT]

Bookmark: Outlet
outlet_2: Tester
    BOOL_OP = OR
    TEST_CLAUSE = CASE_INSENSITIVE_TEST @Value(objectname) BEGINS_WITH Uitlaat
    TEST_MODE = CASE_INSENSITIVE_TEST
    PASSED -> Outlet_coord

Bookmark: flow direction
Note: channel_polygon_input
Junction_4
    -> CenterlineReplacer
Note: CenterlineReplacer : Input
tile_input (input)
    -> Clipper_2 [CLIPPER]
    -> Junction
Note: FeatureJoiner : Left
Junction
    -> Junction_2
Note: tile_input
Junction_2
    -> FeatureJoiner [LEFT]

Bookmark: Azimuth per line segment in 5 x 5m grid
CenterlineReplacer
    MODE = APPROX_CENTER_LINE
    CENTERLINE -> Clipper_2 [CANDIDATE]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> CoordinateExtractor
CoordinateExtractor
    LIST_NAME = _indices
    RECURSIVE = Yes
    MODE = All Coordinates
    -> HorizontalAngleCalculator
HorizontalAngleCalculator
    ANGLE_TYPE = Feature
    UNIT_OUTPUT = DEG
    -> FeatureJoiner_3 [LEFT]
    <Rejected> -> Junction_8
Junction_8

Bookmark: Flip azimuth to correct orientation
FeatureJoiner_3
    ATTR_CONFLICT_RES_LOOKUP = USE_LEFT
    GEOMETRY_HANDLING_LOOKUP = USE_LEFT
    JOIN_KEYS = scid scid AUTO
    JOIN_MODE = Inner
    ATTR_CONFLICT_RES = Prefer Left
    GEOMETRY_HANDLING = Prefer Left
    JOINED -> Flip_azimuth_when_necesary
Flip_azimuth_when_necesary: AttributeManager
    ATTR_TABLE:
      SET_TO diff (real64) = @Evaluate(@abs(@Value(_azimuth)-@Value(average_angle)))
      SET_TO 0_180_diff (real64) = FME_CONDITIONAL:DEFAULT_VALUE'@Evaluate(@Value(diff))'BOOL_OP;OR;COMPOSITE_TEST;1;TEST @Value(diff) > 180'@Evaluate(360-@Value(diff))'FME_NUM_CONDITIONS2___
      SET_TO real_azimuth (real64) = FME_CONDITIONAL:DEFAULT_VALUE'@Evaluate(@Value(_azimuth))'BOOL_OP;OR;COMPOSITE_TEST;1;TEST @Evaluate(@Value(0_180_diff)) > @Evaluate(90)'@Evaluate(@Value(_azimuth)+180)'FME_NUM_CONDITIONS2___
    -> LineOnAreaOverlayer [LINE]

Bookmark: Give flowdirection value to tiles
FeatureJoiner
    ATTR_CONFLICT_RES_LOOKUP = USE_LEFT
    GEOMETRY_HANDLING_LOOKUP = USE_LEFT
    JOIN_KEYS = scid scid AUTO
    JOIN_MODE = Inner
    ATTR_CONFLICT_RES = Prefer Left
    GEOMETRY_HANDLING = Prefer Left
    JOINED -> LineOnAreaOverlayer [AREA]
LineOnAreaOverlayer
    ATTR_ACCUM_MODE = HANDLE_CONFLICT
    ATTR_CONFLICT_RES = ORIGINAL_IF_CONFLICT
    CLEANING_TOLERANCE_LOOKUP = AUTO
    DEAGGREGATE_INPUT = Yes
    OVERLAY_TYPE = LINE_ON_AREA
    OV_ATTR = _overlaps
    CLEANING_TOLERANCE = Automatic
    AREA -> To_many_attributes
To_many_attributes: AttributeManager
    ATTR_TABLE:
      REMOVE diff (real64)
      REMOVE 0_180_diff (real64)
      RENAME_SET_VALUE real_azimuth > flow_direction (real64)
      REMOVE _overlaps (uint32)
      REMOVE objectname (varchar(254))
      REMOVE left (int64)
      REMOVE top (int64)
      REMOVE right (int64)
      REMOVE bottom (int64)
      REMOVE _azimuth (real64)
      REMOVE _X (real64)
      REMOVE _Y (real64)
      REMOVE _angle (real64)
      REMOVE fme_rejection_code (varchar(200))
      REMOVE name (varchar(254))
      REMOVE _clipped (char(3))
      REMOVE _part_number (uint64)
      REMOVE _geometry_label (buffer)
      REMOVE _indices{}.x (real64)
      REMOVE _indices{}.y (real64)
      REMOVE _indices{}.z (real64)
      REMOVE _creation_instance (varchar(200))
      REMOVE _x (varchar(200))
      REMOVE _y (varchar(200))
      REMOVE _z (varchar(200))
      REMOVE _xEnd (varchar(200))
      REMOVE _yEnd (varchar(200))
      REMOVE _zEnd (varchar(200))
      REMOVE average_angle (real64)
      REMOVE objectid (varchar(254))
      REMOVE linkedcomp (varchar(254))
      REMOVE yearof_con (varchar(254))
      REMOVE riskscore (varchar(254))
      REMOVE risklevel (varchar(254))
      REMOVE objectcond (varchar(254))
      REMOVE typeid (varchar(254))
      REMOVE typename (varchar(254))
      REMOVE faultcount (number(19,0))
      REMOVE ultimourl (varchar(254))
      REMOVE timestamp (varchar(254))
      REMOVE objectlati (varchar(254))
      REMOVE objectlong (varchar(254))
      REMOVE objectowne (varchar(254))
      REMOVE objectmana (varchar(254))
      REMOVE _distance (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE inlet_x (real64)
      REMOVE inlet_y (real64)
      REMOVE outlet_x (real64)
      REMOVE outlet_y (real64)
    USER_EXPOSED_ATTRIBUTES = top,bottom,scid,inlet_x,inlet_y,_z,section_azimuth,_indices{0}.x,section_scid,section_name,section_area,section_perimeter,area,perimeter
    -> Split_tiles_into_if_it_has_a_azimuth_value
Split_tiles_into_if_it_has_a_azimuth_value: Tester
    BOOL_OP = OR
    TEST_CLAUSE = TEST flow_direction ATTRIBUTE_IS_MISSING ""
    TEST_MODE = TEST
    PASSED -> Give_empty_tiles_the_nearest_neighbor_value [BASE]
    FAILED -> AttributeRounder
    FAILED -> Give_empty_tiles_the_nearest_neighbor_value [CANDIDATE]
Give_empty_tiles_the_nearest_neighbor_value: NeighborFinder
    ATTR_ACCUM_MODE = Merge Candidate
    ATTR_CONFLICT_RES = Use Base
    CANDIDATES_FIRST = No
    GROUP_BY = scid
    INSERT_VERTEX = No
    MEASURES_FROM_CANDIDATE = Yes
    MEASURE_TYPE = Continuous
    MODE = Bases and Candidates
    TREAT_POLYGON_AS = Lines
    MATCHED -> AttributeRounder
AttributeRounder
    PLACES = 4
    ROUND_TYPE_TCL = round
    SRC_ATTRS = flow_direction
    ROUND_TYPE = Nearest
    -> flow_direction (output)

Bookmark: Notes on feature
Note: This feature calculates the flow direction of tiles in the side channel. This is calculated by deriving the centerline of the channel polygons, and then calculating the angle relative to north of the centerline for each tile. / For tiles that do not directly intersect the centerline, the value of the nearest neightbor is used. / This is a static feature (does not update). If this eventually becomes a feature that is update more frequently (yearly) then it should be moved to the observations table instead.

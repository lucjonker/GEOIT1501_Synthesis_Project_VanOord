FME workspace feature_flowdirection.fmw

Parameters:
- SourceDataset_POSTGIS_7 = DBconnection1   # Connection
- DestDataset_POSTGRES = DBconnection1   # Connection
- SourceDataset_SHAPEFILE_7 = /Users/michel/Desktop/Geomatics/Year_2/Synthesis/QGIS/Bakenhof_shapefile/Inlet_Outlet/Only_inlet_and_outlet.shp   # Source Esri Shapefile(s)
- SourceDataset_SHAPEFILE = /Users/michel/Desktop/Geomatics/Year_2/Synthesis/QGIS/Bakenhof_shapefile/Inlet_Outlet/All_inlet_and_outlet.shp   # Source Esri Shapefile(s)

Readers:
- POSTGIS_2: POSTGIS from $(SourceDataset_POSTGIS_7)
- SHAPEFILE_2: SHAPEFILE from $(SourceDataset_SHAPEFILE)
- SHAPEFILE_3: SHAPEFILE from $(SourceDataset_SHAPEFILE_7)

Writers:
- POSTGRES_1: POSTGRES to $(DestDataset_POSTGRES)

All_inlet_and_outlet (reader SHAPEFILE_2)
    attributes: scid varchar(80), objectname varchar(80)
Only_inlet_and_outlet (reader SHAPEFILE_3)
    attributes: objectid varchar(254), objectname varchar(254), linkedcomp varchar(254), yearof_con varchar(254), riskscore varchar(254), risklevel varchar(254), objectcond varchar(254), typeid varchar(254), typename varchar(254), faultcount number(19,0), ultimourl varchar(254), timestamp varchar(254), objectlati varchar(254), objectlong varchar(254), objectowne varchar(254), objectmana varchar(254)
    -> Reprojector_3
Reprojector_3
    DEST = Amersfoort-RDNew
    INTERPOLATION_TYPE = NearestNeighbor
    RASTER_CELL_SIZE = PreserveCells
    RASTER_TOLERANCE = 0.0
    REPROJECTED -> NeighborFinder_3 [BASE]
CenterlineReplacer
    MODE = APPROX_CENTER_LINE
    CENTERLINE -> Clipper_2 [CANDIDATE]
NeighborFinder_3
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> VertexCreator_7
Note: Make your own with your local data and connect it to the feature you are making
VertexCreator_7
    MEASURE_TYPE_LOOKUP = CONTINUOUS
    MODE = REPLACE
    REMOVE_ATTRIBUTES = No
    XVAL = @Value(_closest_base_x)
    YVAL = @Value(_closest_base_y)
    MEASURE_TYPE = Continuous
    MODE_NAME = Replace with Point
    -> Inlet_2
    -> outlet_2

Bookmark: Database Data (bakenhof filtered)
side_channels (reader POSTGIS_2)
    attributes: scid int4,PrimaryKey, name varchar(254), area numeric(1000,500), perimeter numeric(1000,500)
    -> NeighborFinder_3 [CANDIDATE]
    -> CenterlineReplacer
tiles (reader POSTGIS_2)
    attributes: tid int4,PrimaryKey, left int8, top int8, right int8, bottom int8, scid int4
    -> Clipper_2 [CLIPPER]
    -> LineOnAreaOverlayer [AREA]

Bookmark: Inlet
Inlet_2: Tester
    BOOL_OP = OR
    TEST_CLAUSE = CASE_INSENSITIVE_TEST @Value(objectname) BEGINS_WITH Inlaat
    TEST_MODE = CASE_INSENSITIVE_TEST
    PASSED -> AttributeCreator
AttributeCreator
    ATTR_TABLE = SET_TO id_dummy (real64) = @Evaluate(1)
    -> Inlet_coord

Bookmark: Angle inlet to outlet
Inlet_coord: CoordinateExtractor
    IND = 0
    RECURSIVE = No
    X_ATTR = inlet_x
    Y_ATTR = inlet_y
    Z_ATTR = _z
    MODE = Specify Coordinate
    -> FeatureMerger [REQUESTOR]
Outlet_coord: CoordinateExtractor
    IND = 0
    RECURSIVE = No
    X_ATTR = outlet_x
    Y_ATTR = outlet_y
    Z_ATTR = _z
    MODE = Specify Coordinate
    -> FeatureMerger [SUPPLIER]
FeatureMerger
    ATTR_ACCUM_MODE = Merge Supplier
    ATTR_CONFLICT_RES_LOOKUP = REQUESTOR_IF_CONFLICT
    IGNORE_NULLS = No
    JOIN_KEYS = @Value(scid) @Value(scid) AUTO
    MERGE_TYPE_VAL = ATTRIBUTES
    PROCESS_DUPS = NO
    REJECT_NULL_MISSING_KEYS = No
    SUPPLIERS_FIRST = Yes
    ATTR_CONFLICT_RES = Use Requestor
    MERGE_TYPE = Attributes Only
    MERGED -> AttributeManager_3

Bookmark: Outlet
outlet_2: Tester
    BOOL_OP = OR
    TEST_CLAUSE = CASE_INSENSITIVE_TEST @Value(objectname) BEGINS_WITH Uitlaat
    TEST_MODE = CASE_INSENSITIVE_TEST
    PASSED -> AttributeCreator_2
AttributeCreator_2
    ATTR_TABLE = SET_TO id_dummy (real64) = @Evaluate(1)
    -> Outlet_coord

Bookmark: Compute flow direction
AttributeManager_3
    ATTR_TABLE:
      REMOVE id_dummy (real64)
      SET_TO average_angle (real64) = @Evaluate(360+(@atan2(@Value(outlet_x)-@Value(inlet_x),@Value(outlet_y)-@Value(inlet_y)))*180/@pi())
    USER_EXPOSED_ATTRIBUTES = average_angle
    -> Add_avg_azimuth [SUPPLIER]
StatisticsCalculator
    ATTR_ACCUM_MODE = None
    CALCULATION_MODE = NUMERIC
    FEAT_STATS = flow_direction,NUMERIC_MODE,,,,,MEAN,,,,,,,,
    GROUP_BY = tid
    SUMMARY -> Tester_4
Tester_4
    BOOL_OP = OR
    TEST_CLAUSE = TEST tid NOT_ATTRIBUTE_IS_MISSING ""
    TEST_MODE = TEST
    PASSED -> AttributeManager
AttributeManager
    USER_EXPOSED_ATTRIBUTES = gid,flowdirection.mean
    -> AttributeRounder
AttributeRounder
    PLACES = 4
    ROUND_TYPE_TCL = round
    SRC_ATTRS = flow_direction.mean
    ROUND_TYPE = Nearest
    -> tile_observations (writer POSTGRES_1)
Terminator
    MESSAGE = Translation Terminated

Bookmark: Azimuth per line segment in 5 x 5m grid
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> Deaggregator
Deaggregator
    ATTR_ACCUM_MODE = HANDLE_CONFLICT
    ATTR_CONFLICT_RES = INCOMING_IF_CONFLICT
    EXPLODE_INSTANCES = No
    GEOM_LABEL_FIELD = _geometry_label
    LIST_ATTR_MODE_LOOKUP = LEAN
    PART_NUMBER_FIELD = _part_number
    RECURSIVE = No
    SPLIT_COMPOSITES = No
    DEAGGREGATED -> CoordinateExtractor
CoordinateExtractor
    LIST_NAME = _indices
    RECURSIVE = Yes
    MODE = All Coordinates
    -> HorizontalAngleCalculator
HorizontalAngleCalculator
    ANGLE_TYPE = Feature
    UNIT_OUTPUT = DEG
    -> Add_avg_azimuth [REQUESTOR]
    <Rejected> -> Terminator

Bookmark: Flip azimuth to correct orientation
Add_avg_azimuth: FeatureMerger
    ATTR_ACCUM_MODE = Merge Supplier
    ATTR_CONFLICT_RES_LOOKUP = REQUESTOR_IF_CONFLICT
    IGNORE_NULLS = No
    JOIN_KEYS = @Value(scid) @Value(scid) AUTO
    MERGE_TYPE_VAL = ATTRIBUTES
    PROCESS_DUPS = NO
    REJECT_NULL_MISSING_KEYS = No
    SUPPLIERS_FIRST = Yes
    ATTR_CONFLICT_RES = Use Requestor
    MERGE_TYPE = Attributes Only
    MERGED -> Flip_azimuth_when_necesary
Flip_azimuth_when_necesary: AttributeManager
    ATTR_TABLE:
      SET_TO diff (real64) = @Evaluate(@abs(@Value(_azimuth)-@Value(average_angle)))
      SET_TO 0_180_diff (real64) = FME_CONDITIONAL:DEFAULT_VALUE'@Evaluate(@Value(diff))'BOOL_OP;OR;COMPOSITE_TEST;1;TEST @Value(diff) > 180'@Evaluate(360-@Value(diff))'FME_NUM_CONDITIONS2___
      SET_TO real_azimuth (real64) = FME_CONDITIONAL:DEFAULT_VALUE'@Evaluate(@Value(_azimuth))'BOOL_OP;OR;COMPOSITE_TEST;1;TEST @Evaluate(@Value(0_180_diff)) > @Evaluate(90)'@Evaluate(@Value(_azimuth)+180)'FME_NUM_CONDITIONS2___
    -> LineOnAreaOverlayer [LINE]

Bookmark: Give flowdirection value to tiles
LineOnAreaOverlayer
    ATTR_ACCUM_MODE = HANDLE_CONFLICT
    ATTR_CONFLICT_RES = ORIGINAL_IF_CONFLICT
    CLEANING_TOLERANCE_LOOKUP = AUTO
    DEAGGREGATE_INPUT = Yes
    OVERLAY_TYPE = LINE_ON_AREA
    OV_ATTR = _overlaps
    CLEANING_TOLERANCE = Automatic
    AREA -> To_many_attributes
To_many_attributes: AttributeManager
    ATTR_TABLE:
      REMOVE diff (real64)
      REMOVE 0_180_diff (real64)
      RENAME_SET_VALUE real_azimuth > flow_direction (real64)
      REMOVE _overlaps (uint32)
      REMOVE objectname (varchar(254))
      REMOVE left (int64)
      REMOVE top (int64)
      REMOVE right (int64)
      REMOVE bottom (int64)
      REMOVE _azimuth (real64)
      REMOVE _X (real64)
      REMOVE _Y (real64)
      REMOVE _angle (real64)
      REMOVE fme_rejection_code (varchar(200))
      REMOVE name (varchar(254))
      REMOVE area (number(1000,500))
      REMOVE perimeter (number(1000,500))
      REMOVE _clipped (char(3))
      REMOVE _part_number (uint64)
      REMOVE _geometry_label (buffer)
      REMOVE _indices{}.x (real64)
      REMOVE _indices{}.y (real64)
      REMOVE _indices{}.z (real64)
      REMOVE _creation_instance (varchar(200))
      REMOVE _x (varchar(200))
      REMOVE _y (varchar(200))
      REMOVE _z (varchar(200))
      REMOVE _xEnd (varchar(200))
      REMOVE _yEnd (varchar(200))
      REMOVE _zEnd (varchar(200))
      REMOVE average_angle (real64)
      REMOVE objectid (varchar(254))
      REMOVE linkedcomp (varchar(254))
      REMOVE yearof_con (varchar(254))
      REMOVE riskscore (varchar(254))
      REMOVE risklevel (varchar(254))
      REMOVE objectcond (varchar(254))
      REMOVE typeid (varchar(254))
      REMOVE typename (varchar(254))
      REMOVE faultcount (number(19,0))
      REMOVE ultimourl (varchar(254))
      REMOVE timestamp (varchar(254))
      REMOVE objectlati (varchar(254))
      REMOVE objectlong (varchar(254))
      REMOVE objectowne (varchar(254))
      REMOVE objectmana (varchar(254))
      REMOVE _distance (real64)
      REMOVE _candidate_angle (real64)
      REMOVE _candidate_label_angle (real64)
      REMOVE _closest_candidate_x (real64)
      REMOVE _closest_candidate_y (real64)
      REMOVE _closest_base_x (real64)
      REMOVE _closest_base_y (real64)
      REMOVE inlet_x (real64)
      REMOVE inlet_y (real64)
      REMOVE outlet_x (real64)
      REMOVE outlet_y (real64)
    USER_EXPOSED_ATTRIBUTES = top,bottom,scid,inlet_x,inlet_y,_z,section_azimuth,_indices{0}.x,section_scid,section_name,section_area,section_perimeter
    -> Split_tiles_into_if_it_has_a_azimuth_value
Split_tiles_into_if_it_has_a_azimuth_value: Tester
    BOOL_OP = OR
    TEST_CLAUSE = TEST flow_direction ATTRIBUTE_IS_MISSING ""
    TEST_MODE = TEST
    PASSED -> Give_emty_tiles_the_nearest_neighbor_value [BASE]
    FAILED -> Give_emty_tiles_the_nearest_neighbor_value [CANDIDATE]
    FAILED -> Inspector_8
    FAILED -> StatisticsCalculator
Give_emty_tiles_the_nearest_neighbor_value: NeighborFinder
    ATTR_ACCUM_MODE = Merge Candidate
    ATTR_CONFLICT_RES = Use Base
    CANDIDATES_FIRST = No
    GROUP_BY = scid
    INSERT_VERTEX = No
    MEASURES_FROM_CANDIDATE = Yes
    MEASURE_TYPE = Continuous
    MODE = Bases and Candidates
    TREAT_POLYGON_AS = Lines
    MATCHED -> Inspector_8
    MATCHED -> StatisticsCalculator
Inspector_8

Bookmark: WriteToDatabase(WIP)
tile_observations (writer POSTGRES_1)
    attributes: tid int4,PrimaryKey, flow_direction_mean float8

FME workspace feature_distance_to_bank.fmw

Parameters:
- SourceDataset_POSTGIS = DBconnection1   # Connection
- SourceDataset_POSTGIS_3 = DBconnection1   # Connection

Readers:
- POSTGIS_1: POSTGIS from $(SourceDataset_POSTGIS)
- POSTGIS_2: POSTGIS from $(SourceDataset_POSTGIS_3)

tiles (reader POSTGIS_2)
    attributes: tid int4,PrimaryKey, left int8, top int8, right int8, bottom int8, scid int4, min_flow_threshold int8
    -> Channelselector_3
Channelselector_3: Tester
    BOOL_OP = OR
    TEST_CLAUSE = TEST @Value(scid) = 5
    TEST_MODE = TEST
    PASSED -> CenterPointReplacer
CenterPointReplacer
    POINTTYPE = CENTER
    POINT -> NeighborFinder [BASE]
side_channels (reader POSTGIS_1)
    attributes: scid int4,PrimaryKey, name varchar(254), area numeric(1000,500), perimeter numeric(1000,500), groynevak bool, channel_connections int2, tidal bool, Bank bool, channel_length float4, inner_outer text
    -> Channelselector
Channelselector: Tester
    BOOL_OP = OR
    TEST_CLAUSE = TEST @Value(scid) = 5
    TEST_MODE = TEST
    PASSED -> NeighborFinder [CANDIDATE]
NeighborFinder
    ATTR_ACCUM_MODE = Merge Candidate
    ATTR_CONFLICT_RES = Use Base
    CANDIDATES_FIRST = No
    INSERT_VERTEX = No
    K = 1
    MEASURES_FROM_CANDIDATE = Yes
    MEASURE_TYPE = Continuous
    MODE = Bases and Candidates
    TREAT_POLYGON_AS = Lines
    MATCHED -> AttributeManager
AttributeManager
    ATTR_TABLE:
      REMOVE left (int64)
      REMOVE top (int64)
      REMOVE right (int64)
      REMOVE bottom (int64)
      REMOVE scid (int32)
      REMOVE min_flow_threshold (int64)
      REMOVE name (varchar(254))
      REMOVE area (number(1000,500))
      REMOVE perimeter (number(1000,500))
      REMOVE groynevak (logical)
      REMOVE channel_connections (int16)
      REMOVE tidal (logical)
      REMOVE Bank (logical)
      REMOVE channel_length (real32)
      REMOVE inner_outer (buffer)
      RENAME_SET_VALUE _distance > distance_to_bank (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
    -> AttributeRounder_2
AttributeRounder_2
    PLACES = 3
    ROUND_TYPE_TCL = round
    SRC_ATTRS = distance_to_bank
    ROUND_TYPE = Nearest

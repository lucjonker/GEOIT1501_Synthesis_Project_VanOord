FME workspace feature_upstream_discharge.fmw

Parameters:
- SourceDataset_CSV2_3 = C:\Users\yairr\OneDrive - Delft University of Technology\Michel Beeren's files - Van Oord Synthesis Project\00_Data\RWS_data\afvoer_data_full\20251013_054.csv   # Source CSV (Comma Separated Value) File(s)
- SourceDataset_CSV2 = C:\Users\yairr\OneDrive - Delft University of Technology\Michel Beeren's files - Van Oord Synthesis Project\00_Data\RWS_data\test_afvoerdata_RWS\20251013_010.csv   # Source CSV (Comma Separated Value) File(s)
- SourceDataset_POSTGIS_7 = featurebase   # Connection
- DestDataset_POSTGRES = featurebase   # Connection

Readers:
- CSV2_1: CSV2 from $(SourceDataset_CSV2) in EPSG:25831
- CSV2_2: CSV2 from $(SourceDataset_CSV2_3) in EPSG:25831
- POSTGIS_1: POSTGIS from $(SourceDataset_POSTGIS_7)

Writers:
- POSTGRES_1: POSTGRES to $(DestDataset_POSTGRES)

CSV (reader CSV2_1)
    attributes: MEETPUNT_IDENTIFICATIE varchar(11), WAARNEMINGDATUM varchar(10), WAARNEMINGTIJD (MET/CET) time, NUMERIEKEWAARDE real64, X x_coordinate, Y y_coordinate
    -> DateTimeConverter
    -> Aggregator
Aggregator
    ACCUM_ATTRS = None
    AGGREGATE_TYPE = Homogeneous Collection (If Possible)
    GROUP_BY = MEETPUNT_IDENTIFICATIE
    MODE = Geometry - Assemble One Level
    SEP = ,
DateTimeConverter
    DATETIME_ATTR = WAARNEMINGDATUM
    IN_FORMAT = %d-%m-%Y$
    OUT_FORMAT = %Y
    PASSTHROUGH = NO
    REPAIR_INPUT = YES
    -> Tester_3
Tester_3
    BOOL_OP = OR
    TEST_CLAUSE = DATETIME_TEST @Value(WAARNEMINGDATUM) = 2023
    TEST_MODE = DATETIME_TEST
    PASSED -> Tester_2
Tester_2
    BOOL_OP = OR
    TEST_CLAUSE = TEST @Value(NUMERIEKEWAARDE) < 10000
    TEST_MODE = TEST
    PASSED -> stats_2023
stats_2023: StatisticsCalculator
    ATTR_ACCUM_MODE = None
    CALCULATION_MODE = NUMERIC
    FEAT_STATS = NUMERIEKEWAARDE,NUMERIC_MODE,MIN,MAX,COUNT,,MEAN,,,,,,,,
    GROUP_BY = MEETPUNT_IDENTIFICATIE
CSV (reader CSV2_2)
    attributes: MEETPUNT_IDENTIFICATIE varchar(11), WAARNEMINGDATUM varchar(10), WAARNEMINGTIJD (MET/CET) time, NUMERIEKEWAARDE real64, X x_coordinate, Y y_coordinate
    -> DateTimeConverter_2
DateTimeConverter_2
    DATETIME_ATTR = WAARNEMINGDATUM
    IN_FORMAT = %d-%m-%Y$
    OUT_FORMAT = %Y
    PASSTHROUGH = NO
    REPAIR_INPUT = YES
    -> Tester_5
Tester_5
    BOOL_OP = OR
    TEST_CLAUSE = DATETIME_TEST @Value(WAARNEMINGDATUM) = 2025
    TEST_MODE = DATETIME_TEST
    PASSED -> Tester_4
    FAILED -> Tester_6
Tester_4
    BOOL_OP = OR
    TEST_CLAUSE = TEST @Value(NUMERIEKEWAARDE) < 10000
    TEST_MODE = TEST
    PASSED -> stats_2025
stats_2025: StatisticsCalculator
    ATTR_ACCUM_MODE = All
    CALCULATION_MODE = NUMERIC
    FEAT_STATS = NUMERIEKEWAARDE,NUMERIC_MODE,MIN,MAX,COUNT,,MEAN,,,,,,,,
    GROUP_BY = MEETPUNT_IDENTIFICATIE
Tester_6
    BOOL_OP = OR
    TEST_CLAUSE = TEST @Value(NUMERIEKEWAARDE) < 10000
    TEST_MODE = TEST
    PASSED -> stats_2024
stats_2024: StatisticsCalculator
    ATTR_ACCUM_MODE = None
    CALCULATION_MODE = NUMERIC
    FEAT_STATS = NUMERIEKEWAARDE,NUMERIC_MODE,MIN,MAX,COUNT,,MEAN,,,,,,,,
    GROUP_BY = MEETPUNT_IDENTIFICATIE
side_channels (reader POSTGIS_1)
    attributes: scid int4,PrimaryKey, name varchar(254), area numeric(1000,500), perimeter numeric(1000,500)
side_channels (writer POSTGRES_1)
    attributes: scid int4, area float4, perimeter float4
